--
-- MahindraComviva-GNOC-PreTUPs-MIB.my
-- MIB generated by MG-SOFT Visual MIB Builder 2010 Version 8.0  Build 410
-- Friday, October 07, 2016 at 17:47:24
--

	MahindraComviva-GNOC-PreTUPs-MIB DEFINITIONS ::= BEGIN
 
		IMPORTS
			comviva, alarmObjects			
				FROM Comviva			
			Integer32, OBJECT-TYPE, OBJECT-IDENTITY, NOTIFICATION-TYPE			
				FROM SNMPv2-SMI;
	
	
--
-- Node definitions
--
	
		-- 1.3.6.1.4.1.19338.0.1
		exitStatus OBJECT-TYPE
			SYNTAX Integer32
			MAX-ACCESS read-write
			STATUS current
			DESCRIPTION
				"Description."
			::= { alarmObjects 1 }

		
		-- 1.3.6.1.4.1.19338.0.2
		alarmString OBJECT-TYPE
			SYNTAX OCTET STRING
			MAX-ACCESS read-write
			STATUS current
			DESCRIPTION
				"Description."
			::= { alarmObjects 2 }

		
		-- 1.3.6.1.4.1.19338.0.3
		misc OBJECT-TYPE
			SYNTAX OCTET STRING
			MAX-ACCESS read-write
			STATUS current
			DESCRIPTION
				"Description."
			::= { alarmObjects 3 }

		
		-- 1.3.6.1.4.1.19338.0.4
		alarmType OBJECT-TYPE
			SYNTAX OCTET STRING
			MAX-ACCESS read-write
			STATUS current
			DESCRIPTION
				"Description."
			::= { alarmObjects 4 }

		
		-- 1.3.6.1.4.1.19338.0.5
		alarmStatus OBJECT-TYPE
			SYNTAX OCTET STRING
			MAX-ACCESS read-write
			STATUS current
			DESCRIPTION
				"Description."
			::= { alarmObjects 5 }

		
		-- 1.3.6.1.4.1.19338.19
		preTUPs OBJECT-IDENTITY
			STATUS current
			DESCRIPTION 
				"Sub-tree for specific Product"
			::= { comviva 19 }

		
		-- 1.3.6.1.4.1.19338.19.2
		instance1 OBJECT-IDENTITY
			STATUS current
			DESCRIPTION 
				"Description of Product :"
			::= { preTUPs 2 }

		
		-- 1.3.6.1.4.1.19338.19.2.1
		network1 OBJECT-IDENTITY
			STATUS current
			DESCRIPTION 
				"Description."
			::= { instance1 1 }

		
		-- 1.3.6.1.4.1.19338.19.2.1.1
		all OBJECT-IDENTITY
			STATUS current
			DESCRIPTION 
				"Description."
			::= { network1 1 }

		
		-- 1.3.6.1.4.1.19338.19.2.1.1.1
		totalINCount1 OBJECT-TYPE
			SYNTAX OCTET STRING
			MAX-ACCESS read-write
			STATUS current
			DESCRIPTION
				"Description."
			::= { all 1 }

		
		-- 1.3.6.1.4.1.19338.19.2.1.1.2
		successCount1 OBJECT-TYPE
			SYNTAX OCTET STRING
			MAX-ACCESS read-write
			STATUS current
			DESCRIPTION
				"Description."
			::= { all 2 }

		
		-- 1.3.6.1.4.1.19338.19.2.1.1.3
		failCount1 OBJECT-TYPE
			SYNTAX OCTET STRING
			MAX-ACCESS read-write
			STATUS current
			DESCRIPTION
				"Description."
			::= { all 3 }

		
		-- 1.3.6.1.4.1.19338.19.2.1.1.4
		refusedCount1 OBJECT-TYPE
			SYNTAX OCTET STRING
			MAX-ACCESS read-write
			STATUS current
			DESCRIPTION
				"Description."
			::= { all 4 }

		
		-- 1.3.6.1.4.1.19338.19.2.1.2
		accinfo OBJECT-IDENTITY
			STATUS current
			DESCRIPTION 
				"Description."
			::= { network1 2 }

		
		-- 1.3.6.1.4.1.19338.19.2.1.2.1
		totalINCount2 OBJECT-TYPE
			SYNTAX OCTET STRING
			MAX-ACCESS read-write
			STATUS current
			DESCRIPTION
				"Description."
			::= { accinfo 1 }

		
		-- 1.3.6.1.4.1.19338.19.2.1.2.2
		successCount2 OBJECT-TYPE
			SYNTAX OCTET STRING
			MAX-ACCESS read-write
			STATUS current
			DESCRIPTION
				"Description."
			::= { accinfo 2 }

		
		-- 1.3.6.1.4.1.19338.19.2.1.2.3
		failCount2 OBJECT-TYPE
			SYNTAX OCTET STRING
			MAX-ACCESS read-write
			STATUS current
			DESCRIPTION
				"Description."
			::= { accinfo 3 }

		
		-- 1.3.6.1.4.1.19338.19.2.1.2.4
		refusedCount2 OBJECT-TYPE
			SYNTAX OCTET STRING
			MAX-ACCESS read-write
			STATUS current
			DESCRIPTION
				"Description."
			::= { accinfo 4 }

		
		-- 1.3.6.1.4.1.19338.19.2.1.3
		adm OBJECT-IDENTITY
			STATUS current
			DESCRIPTION 
				"Description."
			::= { network1 3 }

		
		-- 1.3.6.1.4.1.19338.19.2.1.3.1
		totalINCount3 OBJECT-TYPE
			SYNTAX OCTET STRING
			MAX-ACCESS read-write
			STATUS current
			DESCRIPTION
				"Description."
			::= { adm 1 }

		
		-- 1.3.6.1.4.1.19338.19.2.1.3.2
		successCount3 OBJECT-TYPE
			SYNTAX OCTET STRING
			MAX-ACCESS read-write
			STATUS current
			DESCRIPTION
				"Description."
			::= { adm 2 }

		
		-- 1.3.6.1.4.1.19338.19.2.1.3.3
		failCount3 OBJECT-TYPE
			SYNTAX OCTET STRING
			MAX-ACCESS read-write
			STATUS current
			DESCRIPTION
				"Description."
			::= { adm 3 }

		
		-- 1.3.6.1.4.1.19338.19.2.1.3.4
		refusedCount3 OBJECT-TYPE
			SYNTAX OCTET STRING
			MAX-ACCESS read-write
			STATUS current
			DESCRIPTION
				"Description."
			::= { adm 4 }

		
		-- 1.3.6.1.4.1.19338.19.2.1.4
		bar OBJECT-IDENTITY
			STATUS current
			DESCRIPTION 
				"Description."
			::= { network1 4 }

		
		-- 1.3.6.1.4.1.19338.19.2.1.4.1
		totalINCount4 OBJECT-TYPE
			SYNTAX OCTET STRING
			MAX-ACCESS read-write
			STATUS current
			DESCRIPTION
				"Description."
			::= { bar 1 }

		
		-- 1.3.6.1.4.1.19338.19.2.1.4.2
		successCount4 OBJECT-TYPE
			SYNTAX OCTET STRING
			MAX-ACCESS read-write
			STATUS current
			DESCRIPTION
				"Description."
			::= { bar 2 }

		
		-- 1.3.6.1.4.1.19338.19.2.1.4.3
		failCount4 OBJECT-TYPE
			SYNTAX OCTET STRING
			MAX-ACCESS read-write
			STATUS current
			DESCRIPTION
				"Description."
			::= { bar 3 }

		
		-- 1.3.6.1.4.1.19338.19.2.1.4.4
		frefusedCount4 OBJECT-TYPE
			SYNTAX OCTET STRING
			MAX-ACCESS read-write
			STATUS current
			DESCRIPTION
				"Description."
			::= { bar 4 }

		
		-- 1.3.6.1.4.1.19338.19.2.1.5
		barUser OBJECT-IDENTITY
			STATUS current
			DESCRIPTION 
				"Description."
			::= { network1 5 }

		
		-- 1.3.6.1.4.1.19338.19.2.1.5.1
		totalINCount5 OBJECT-TYPE
			SYNTAX OCTET STRING
			MAX-ACCESS read-write
			STATUS current
			DESCRIPTION
				"Description."
			::= { barUser 1 }

		
		-- 1.3.6.1.4.1.19338.19.2.1.5.2
		successCount5 OBJECT-TYPE
			SYNTAX OCTET STRING
			MAX-ACCESS read-write
			STATUS current
			DESCRIPTION
				"Description."
			::= { barUser 2 }

		
		-- 1.3.6.1.4.1.19338.19.2.1.5.3
		failCount5 OBJECT-TYPE
			SYNTAX OCTET STRING
			MAX-ACCESS read-write
			STATUS current
			DESCRIPTION
				"Description."
			::= { barUser 3 }

		
		-- 1.3.6.1.4.1.19338.19.2.1.5.4
		refusedCount5 OBJECT-TYPE
			SYNTAX OCTET STRING
			MAX-ACCESS read-write
			STATUS current
			DESCRIPTION
				"Description."
			::= { barUser 4 }

		
		-- 1.3.6.1.4.1.19338.19.2.1.6
		c2cTRFENQ OBJECT-IDENTITY
			STATUS current
			DESCRIPTION 
				"Description."
			::= { network1 6 }

		
		-- 1.3.6.1.4.1.19338.19.2.1.6.1
		totalINCount6 OBJECT-TYPE
			SYNTAX OCTET STRING
			MAX-ACCESS read-write
			STATUS current
			DESCRIPTION
				"Description."
			::= { c2cTRFENQ 1 }

		
		-- 1.3.6.1.4.1.19338.19.2.1.6.2
		successCount6 OBJECT-TYPE
			SYNTAX OCTET STRING
			MAX-ACCESS read-write
			STATUS current
			DESCRIPTION
				"Description."
			::= { c2cTRFENQ 2 }

		
		-- 1.3.6.1.4.1.19338.19.2.1.6.3
		failCount6 OBJECT-TYPE
			SYNTAX OCTET STRING
			MAX-ACCESS read-write
			STATUS current
			DESCRIPTION
				"Description."
			::= { c2cTRFENQ 3 }

		
		-- 1.3.6.1.4.1.19338.19.2.1.6.4
		refusedCount6 OBJECT-TYPE
			SYNTAX OCTET STRING
			MAX-ACCESS read-write
			STATUS current
			DESCRIPTION
				"Description."
			::= { c2cTRFENQ 4 }

		
		-- 1.3.6.1.4.1.19338.19.2.1.7
		c2sBal OBJECT-IDENTITY
			STATUS current
			DESCRIPTION 
				"Description."
			::= { network1 7 }

		
		-- 1.3.6.1.4.1.19338.19.2.1.7.1
		totalINCount7 OBJECT-TYPE
			SYNTAX OCTET STRING
			MAX-ACCESS read-write
			STATUS current
			DESCRIPTION
				"Description."
			::= { c2sBal 1 }

		
		-- 1.3.6.1.4.1.19338.19.2.1.7.2
		successCount7 OBJECT-TYPE
			SYNTAX OCTET STRING
			MAX-ACCESS read-write
			STATUS current
			DESCRIPTION
				"Description."
			::= { c2sBal 2 }

		
		-- 1.3.6.1.4.1.19338.19.2.1.7.3
		failCount7 OBJECT-TYPE
			SYNTAX OCTET STRING
			MAX-ACCESS read-write
			STATUS current
			DESCRIPTION
				"Description."
			::= { c2sBal 3 }

		
		-- 1.3.6.1.4.1.19338.19.2.1.7.4
		refusedCount7 OBJECT-TYPE
			SYNTAX OCTET STRING
			MAX-ACCESS read-write
			STATUS current
			DESCRIPTION
				"Description."
			::= { c2sBal 4 }

		
		-- 1.3.6.1.4.1.19338.19.2.1.8
		c2sCpn OBJECT-IDENTITY
			STATUS current
			DESCRIPTION 
				"Description."
			::= { network1 8 }

		
		-- 1.3.6.1.4.1.19338.19.2.1.8.1
		totalINCount8 OBJECT-TYPE
			SYNTAX OCTET STRING
			MAX-ACCESS read-write
			STATUS current
			DESCRIPTION
				"Description."
			::= { c2sCpn 1 }

		
		-- 1.3.6.1.4.1.19338.19.2.1.8.2
		successCount8 OBJECT-TYPE
			SYNTAX OCTET STRING
			MAX-ACCESS read-write
			STATUS current
			DESCRIPTION
				"Description."
			::= { c2sCpn 2 }

		
		-- 1.3.6.1.4.1.19338.19.2.1.8.3
		failCount8 OBJECT-TYPE
			SYNTAX OCTET STRING
			MAX-ACCESS read-write
			STATUS current
			DESCRIPTION
				"Description."
			::= { c2sCpn 3 }

		
		-- 1.3.6.1.4.1.19338.19.2.1.8.4
		refusedCount8 OBJECT-TYPE
			SYNTAX OCTET STRING
			MAX-ACCESS read-write
			STATUS current
			DESCRIPTION
				"Description."
			::= { c2sCpn 4 }

		
		-- 1.3.6.1.4.1.19338.19.2.1.9
		c2sDAILYTR OBJECT-IDENTITY
			STATUS current
			DESCRIPTION 
				"Description."
			::= { network1 9 }

		
		-- 1.3.6.1.4.1.19338.19.2.1.9.1
		totalINCount9 OBJECT-TYPE
			SYNTAX OCTET STRING
			MAX-ACCESS read-write
			STATUS current
			DESCRIPTION
				"Description."
			::= { c2sDAILYTR 1 }

		
		-- 1.3.6.1.4.1.19338.19.2.1.9.2
		successCount9 OBJECT-TYPE
			SYNTAX OCTET STRING
			MAX-ACCESS read-write
			STATUS current
			DESCRIPTION
				"Description."
			::= { c2sDAILYTR 2 }

		
		-- 1.3.6.1.4.1.19338.19.2.1.9.3
		failCount9 OBJECT-TYPE
			SYNTAX OCTET STRING
			MAX-ACCESS read-write
			STATUS current
			DESCRIPTION
				"Description."
			::= { c2sDAILYTR 3 }

		
		-- 1.3.6.1.4.1.19338.19.2.1.9.4
		refusedCount9 OBJECT-TYPE
			SYNTAX OCTET STRING
			MAX-ACCESS read-write
			STATUS current
			DESCRIPTION
				"Description."
			::= { c2sDAILYTR 4 }

		
		-- 1.3.6.1.4.1.19338.19.2.1.10
		c2sENQ OBJECT-IDENTITY
			STATUS current
			DESCRIPTION 
				"Description."
			::= { network1 10 }

		
		-- 1.3.6.1.4.1.19338.19.2.1.10.1
		totalINCount10 OBJECT-TYPE
			SYNTAX OCTET STRING
			MAX-ACCESS read-write
			STATUS current
			DESCRIPTION
				"Description."
			::= { c2sENQ 1 }

		
		-- 1.3.6.1.4.1.19338.19.2.1.10.2
		successCount10 OBJECT-TYPE
			SYNTAX OCTET STRING
			MAX-ACCESS read-write
			STATUS current
			DESCRIPTION
				"Description."
			::= { c2sENQ 2 }

		
		-- 1.3.6.1.4.1.19338.19.2.1.10.3
		failCount10 OBJECT-TYPE
			SYNTAX OCTET STRING
			MAX-ACCESS read-write
			STATUS current
			DESCRIPTION
				"Description."
			::= { c2sENQ 3 }

		
		-- 1.3.6.1.4.1.19338.19.2.1.10.4
		refusedCount10 OBJECT-TYPE
			SYNTAX OCTET STRING
			MAX-ACCESS read-write
			STATUS current
			DESCRIPTION
				"Description."
			::= { c2sENQ 4 }

		
		-- 1.3.6.1.4.1.19338.19.2.1.11
		c2sLASTTRF OBJECT-IDENTITY
			STATUS current
			DESCRIPTION 
				"Description."
			::= { network1 11 }

		
		-- 1.3.6.1.4.1.19338.19.2.1.11.1
		totalINCount11 OBJECT-TYPE
			SYNTAX OCTET STRING
			MAX-ACCESS read-write
			STATUS current
			DESCRIPTION
				"Description."
			::= { c2sLASTTRF 1 }

		
		-- 1.3.6.1.4.1.19338.19.2.1.11.2
		successCount11 OBJECT-TYPE
			SYNTAX OCTET STRING
			MAX-ACCESS read-write
			STATUS current
			DESCRIPTION
				"Description."
			::= { c2sLASTTRF 2 }

		
		-- 1.3.6.1.4.1.19338.19.2.1.11.3
		failCount11 OBJECT-TYPE
			SYNTAX OCTET STRING
			MAX-ACCESS read-write
			STATUS current
			DESCRIPTION
				"Description."
			::= { c2sLASTTRF 3 }

		
		-- 1.3.6.1.4.1.19338.19.2.1.11.4
		refusedCount11 OBJECT-TYPE
			SYNTAX OCTET STRING
			MAX-ACCESS read-write
			STATUS current
			DESCRIPTION
				"Description."
			::= { c2sLASTTRF 4 }

		
		-- 1.3.6.1.4.1.19338.19.2.1.12
		c2sLASXTRF OBJECT-IDENTITY
			STATUS current
			DESCRIPTION 
				"Description."
			::= { network1 12 }

		
		-- 1.3.6.1.4.1.19338.19.2.1.12.1
		totalINCount12 OBJECT-TYPE
			SYNTAX OCTET STRING
			MAX-ACCESS read-write
			STATUS current
			DESCRIPTION
				"Description."
			::= { c2sLASXTRF 1 }

		
		-- 1.3.6.1.4.1.19338.19.2.1.12.2
		successCount12 OBJECT-TYPE
			SYNTAX OCTET STRING
			MAX-ACCESS read-write
			STATUS current
			DESCRIPTION
				"Description."
			::= { c2sLASXTRF 2 }

		
		-- 1.3.6.1.4.1.19338.19.2.1.12.3
		failCount12 OBJECT-TYPE
			SYNTAX OCTET STRING
			MAX-ACCESS read-write
			STATUS current
			DESCRIPTION
				"Description."
			::= { c2sLASXTRF 3 }

		
		-- 1.3.6.1.4.1.19338.19.2.1.12.4
		refusedCount12 OBJECT-TYPE
			SYNTAX OCTET STRING
			MAX-ACCESS read-write
			STATUS current
			DESCRIPTION
				"Description."
			::= { c2sLASXTRF 4 }

		
		-- 1.3.6.1.4.1.19338.19.2.1.13
		c2sTRFENQ OBJECT-IDENTITY
			STATUS current
			DESCRIPTION 
				"Description."
			::= { network1 13 }

		
		-- 1.3.6.1.4.1.19338.19.2.1.13.1
		totalINCount13 OBJECT-TYPE
			SYNTAX OCTET STRING
			MAX-ACCESS read-write
			STATUS current
			DESCRIPTION
				"Description."
			::= { c2sTRFENQ 1 }

		
		-- 1.3.6.1.4.1.19338.19.2.1.13.2
		successCount13 OBJECT-TYPE
			SYNTAX OCTET STRING
			MAX-ACCESS read-write
			STATUS current
			DESCRIPTION
				"Description."
			::= { c2sTRFENQ 2 }

		
		-- 1.3.6.1.4.1.19338.19.2.1.13.3
		failCount13 OBJECT-TYPE
			SYNTAX OCTET STRING
			MAX-ACCESS read-write
			STATUS current
			DESCRIPTION
				"Description."
			::= { c2sTRFENQ 3 }

		
		-- 1.3.6.1.4.1.19338.19.2.1.13.4
		refusedCount13 OBJECT-TYPE
			SYNTAX OCTET STRING
			MAX-ACCESS read-write
			STATUS current
			DESCRIPTION
				"Description."
			::= { c2sTRFENQ 4 }

		
		-- 1.3.6.1.4.1.19338.19.2.1.14
		c2sUNBLKPN OBJECT-IDENTITY
			STATUS current
			DESCRIPTION 
				"Description."
			::= { network1 14 }

		
		-- 1.3.6.1.4.1.19338.19.2.1.14.1
		totalINCount14 OBJECT-TYPE
			SYNTAX OCTET STRING
			MAX-ACCESS read-write
			STATUS current
			DESCRIPTION
				"Description."
			::= { c2sUNBLKPN 1 }

		
		-- 1.3.6.1.4.1.19338.19.2.1.14.2
		successCount14 OBJECT-TYPE
			SYNTAX OCTET STRING
			MAX-ACCESS read-write
			STATUS current
			DESCRIPTION
				"Description."
			::= { c2sUNBLKPN 2 }

		
		-- 1.3.6.1.4.1.19338.19.2.1.14.3
		failCount14 OBJECT-TYPE
			SYNTAX OCTET STRING
			MAX-ACCESS read-write
			STATUS current
			DESCRIPTION
				"Description."
			::= { c2sUNBLKPN 3 }

		
		-- 1.3.6.1.4.1.19338.19.2.1.14.4
		refusedCount14 OBJECT-TYPE
			SYNTAX OCTET STRING
			MAX-ACCESS read-write
			STATUS current
			DESCRIPTION
				"Description."
			::= { c2sUNBLKPN 4 }

		
		-- 1.3.6.1.4.1.19338.19.2.1.15
		c2sUNBLOCK OBJECT-IDENTITY
			STATUS current
			DESCRIPTION 
				"Description."
			::= { network1 15 }

		
		-- 1.3.6.1.4.1.19338.19.2.1.15.1
		totalINCount15 OBJECT-TYPE
			SYNTAX OCTET STRING
			MAX-ACCESS read-write
			STATUS current
			DESCRIPTION
				"Description."
			::= { c2sUNBLOCK 1 }

		
		-- 1.3.6.1.4.1.19338.19.2.1.15.2
		successCount15 OBJECT-TYPE
			SYNTAX OCTET STRING
			MAX-ACCESS read-write
			STATUS current
			DESCRIPTION
				"Description."
			::= { c2sUNBLOCK 2 }

		
		-- 1.3.6.1.4.1.19338.19.2.1.15.3
		failCount15 OBJECT-TYPE
			SYNTAX OCTET STRING
			MAX-ACCESS read-write
			STATUS current
			DESCRIPTION
				"Description."
			::= { c2sUNBLOCK 3 }

		
		-- 1.3.6.1.4.1.19338.19.2.1.15.4
		refusedCount15 OBJECT-TYPE
			SYNTAX OCTET STRING
			MAX-ACCESS read-write
			STATUS current
			DESCRIPTION
				"Description."
			::= { c2sUNBLOCK 4 }

		
		-- 1.3.6.1.4.1.19338.19.2.1.16
		cARDDL OBJECT-IDENTITY
			STATUS current
			DESCRIPTION 
				"Description."
			::= { network1 16 }

		
		-- 1.3.6.1.4.1.19338.19.2.1.16.1
		totalINCount16 OBJECT-TYPE
			SYNTAX OCTET STRING
			MAX-ACCESS read-write
			STATUS current
			DESCRIPTION
				"Description."
			::= { cARDDL 1 }

		
		-- 1.3.6.1.4.1.19338.19.2.1.16.2
		successCount16 OBJECT-TYPE
			SYNTAX OCTET STRING
			MAX-ACCESS read-write
			STATUS current
			DESCRIPTION
				"Description."
			::= { cARDDL 2 }

		
		-- 1.3.6.1.4.1.19338.19.2.1.16.3
		failCount16 OBJECT-TYPE
			SYNTAX OCTET STRING
			MAX-ACCESS read-write
			STATUS current
			DESCRIPTION
				"Description."
			::= { cARDDL 3 }

		
		-- 1.3.6.1.4.1.19338.19.2.1.16.4
		refusedCount16 OBJECT-TYPE
			SYNTAX OCTET STRING
			MAX-ACCESS read-write
			STATUS current
			DESCRIPTION
				"Description."
			::= { cARDDL 4 }

		
		-- 1.3.6.1.4.1.19338.19.2.1.17
		cCHLAN OBJECT-IDENTITY
			STATUS current
			DESCRIPTION 
				"Description."
			::= { network1 17 }

		
		-- 1.3.6.1.4.1.19338.19.2.1.17.1
		totalINCount17 OBJECT-TYPE
			SYNTAX OCTET STRING
			MAX-ACCESS read-write
			STATUS current
			DESCRIPTION
				"Description."
			::= { cCHLAN 1 }

		
		-- 1.3.6.1.4.1.19338.19.2.1.17.2
		successCount17 OBJECT-TYPE
			SYNTAX OCTET STRING
			MAX-ACCESS read-write
			STATUS current
			DESCRIPTION
				"Description."
			::= { cCHLAN 2 }

		
		-- 1.3.6.1.4.1.19338.19.2.1.17.3
		failCount17 OBJECT-TYPE
			SYNTAX OCTET STRING
			MAX-ACCESS read-write
			STATUS current
			DESCRIPTION
				"Description."
			::= { cCHLAN 3 }

		
		-- 1.3.6.1.4.1.19338.19.2.1.17.4
		refusedCount17 OBJECT-TYPE
			SYNTAX OCTET STRING
			MAX-ACCESS read-write
			STATUS current
			DESCRIPTION
				"Description."
			::= { cCHLAN 4 }

		
		-- 1.3.6.1.4.1.19338.19.2.1.18
		cDPCR OBJECT-IDENTITY
			STATUS current
			DESCRIPTION 
				"Description."
			::= { network1 18 }

		
		-- 1.3.6.1.4.1.19338.19.2.1.18.1
		totalINCount18 OBJECT-TYPE
			SYNTAX OCTET STRING
			MAX-ACCESS read-write
			STATUS current
			DESCRIPTION
				"Description."
			::= { cDPCR 1 }

		
		-- 1.3.6.1.4.1.19338.19.2.1.18.2
		successCount18 OBJECT-TYPE
			SYNTAX OCTET STRING
			MAX-ACCESS read-write
			STATUS current
			DESCRIPTION
				"Description."
			::= { cDPCR 2 }

		
		-- 1.3.6.1.4.1.19338.19.2.1.18.3
		failCount18 OBJECT-TYPE
			SYNTAX OCTET STRING
			MAX-ACCESS read-write
			STATUS current
			DESCRIPTION
				"Description."
			::= { cDPCR 3 }

		
		-- 1.3.6.1.4.1.19338.19.2.1.18.4
		refusedCount18 OBJECT-TYPE
			SYNTAX OCTET STRING
			MAX-ACCESS read-write
			STATUS current
			DESCRIPTION
				"Description."
			::= { cDPCR 4 }

		
		-- 1.3.6.1.4.1.19338.19.2.1.19
		cGMBALREQ OBJECT-IDENTITY
			STATUS current
			DESCRIPTION 
				"Description."
			::= { network1 19 }

		
		-- 1.3.6.1.4.1.19338.19.2.1.19.1
		totalINCount19 OBJECT-TYPE
			SYNTAX OCTET STRING
			MAX-ACCESS read-write
			STATUS current
			DESCRIPTION
				"Description."
			::= { cGMBALREQ 1 }

		
		-- 1.3.6.1.4.1.19338.19.2.1.19.2
		successCount19 OBJECT-TYPE
			SYNTAX OCTET STRING
			MAX-ACCESS read-write
			STATUS current
			DESCRIPTION
				"Description."
			::= { cGMBALREQ 2 }

		
		-- 1.3.6.1.4.1.19338.19.2.1.19.3
		failCount19 OBJECT-TYPE
			SYNTAX OCTET STRING
			MAX-ACCESS read-write
			STATUS current
			DESCRIPTION
				"Description."
			::= { cGMBALREQ 3 }

		
		-- 1.3.6.1.4.1.19338.19.2.1.19.4
		refusedCount19 OBJECT-TYPE
			SYNTAX OCTET STRING
			MAX-ACCESS read-write
			STATUS current
			DESCRIPTION
				"Description."
			::= { cGMBALREQ 4 }

		
		-- 1.3.6.1.4.1.19338.19.2.1.20
		cHANGELANG OBJECT-IDENTITY
			STATUS current
			DESCRIPTION 
				"Description."
			::= { network1 20 }

		
		-- 1.3.6.1.4.1.19338.19.2.1.20.1
		totalINCount20 OBJECT-TYPE
			SYNTAX OCTET STRING
			MAX-ACCESS read-write
			STATUS current
			DESCRIPTION
				"Description."
			::= { cHANGELANG 1 }

		
		-- 1.3.6.1.4.1.19338.19.2.1.20.2
		successCount20 OBJECT-TYPE
			SYNTAX OCTET STRING
			MAX-ACCESS read-write
			STATUS current
			DESCRIPTION
				"Description."
			::= { cHANGELANG 2 }

		
		-- 1.3.6.1.4.1.19338.19.2.1.20.3
		failCount20 OBJECT-TYPE
			SYNTAX OCTET STRING
			MAX-ACCESS read-write
			STATUS current
			DESCRIPTION
				"Description."
			::= { cHANGELANG 3 }

		
		-- 1.3.6.1.4.1.19338.19.2.1.20.4
		refusedCount20 OBJECT-TYPE
			SYNTAX OCTET STRING
			MAX-ACCESS read-write
			STATUS current
			DESCRIPTION
				"Description."
			::= { cHANGELANG 4 }

		
		-- 1.3.6.1.4.1.19338.19.2.1.21
		cPN OBJECT-IDENTITY
			STATUS current
			DESCRIPTION 
				"Description."
			::= { network1 21 }

		
		-- 1.3.6.1.4.1.19338.19.2.1.21.1
		totalINCount21 OBJECT-TYPE
			SYNTAX OCTET STRING
			MAX-ACCESS read-write
			STATUS current
			DESCRIPTION
				"Description."
			::= { cPN 1 }

		
		-- 1.3.6.1.4.1.19338.19.2.1.21.2
		successCount21 OBJECT-TYPE
			SYNTAX OCTET STRING
			MAX-ACCESS read-write
			STATUS current
			DESCRIPTION
				"Description."
			::= { cPN 2 }

		
		-- 1.3.6.1.4.1.19338.19.2.1.21.3
		failCount21 OBJECT-TYPE
			SYNTAX OCTET STRING
			MAX-ACCESS read-write
			STATUS current
			DESCRIPTION
				"Description."
			::= { cPN 3 }

		
		-- 1.3.6.1.4.1.19338.19.2.1.21.4
		refusedCount21 OBJECT-TYPE
			SYNTAX OCTET STRING
			MAX-ACCESS read-write
			STATUS current
			DESCRIPTION
				"Description."
			::= { cPN 4 }

		
		-- 1.3.6.1.4.1.19338.19.2.1.22
		cPREG OBJECT-IDENTITY
			STATUS current
			DESCRIPTION 
				"Description."
			::= { network1 22 }

		
		-- 1.3.6.1.4.1.19338.19.2.1.22.1
		totalINCount22 OBJECT-TYPE
			SYNTAX OCTET STRING
			MAX-ACCESS read-write
			STATUS current
			DESCRIPTION
				"Description."
			::= { cPREG 1 }

		
		-- 1.3.6.1.4.1.19338.19.2.1.22.2
		successCount22 OBJECT-TYPE
			SYNTAX OCTET STRING
			MAX-ACCESS read-write
			STATUS current
			DESCRIPTION
				"Description."
			::= { cPREG 2 }

		
		-- 1.3.6.1.4.1.19338.19.2.1.22.3
		failCount22 OBJECT-TYPE
			SYNTAX OCTET STRING
			MAX-ACCESS read-write
			STATUS current
			DESCRIPTION
				"Description."
			::= { cPREG 3 }

		
		-- 1.3.6.1.4.1.19338.19.2.1.22.4
		refusedCount22 OBJECT-TYPE
			SYNTAX OCTET STRING
			MAX-ACCESS read-write
			STATUS current
			DESCRIPTION
				"Description."
			::= { cPREG 4 }

		
		-- 1.3.6.1.4.1.19338.19.2.1.23
		cRC OBJECT-IDENTITY
			STATUS current
			DESCRIPTION 
				"Description."
			::= { network1 23 }

		
		-- 1.3.6.1.4.1.19338.19.2.1.23.1
		totalINCount23 OBJECT-TYPE
			SYNTAX OCTET STRING
			MAX-ACCESS read-write
			STATUS current
			DESCRIPTION
				"Description."
			::= { cRC 1 }

		
		-- 1.3.6.1.4.1.19338.19.2.1.23.2
		successCount23 OBJECT-TYPE
			SYNTAX OCTET STRING
			MAX-ACCESS read-write
			STATUS current
			DESCRIPTION
				"Description."
			::= { cRC 2 }

		
		-- 1.3.6.1.4.1.19338.19.2.1.23.3
		failCount23 OBJECT-TYPE
			SYNTAX OCTET STRING
			MAX-ACCESS read-write
			STATUS current
			DESCRIPTION
				"Description."
			::= { cRC 3 }

		
		-- 1.3.6.1.4.1.19338.19.2.1.23.4
		refusedCount23 OBJECT-TYPE
			SYNTAX OCTET STRING
			MAX-ACCESS read-write
			STATUS current
			DESCRIPTION
				"Description."
			::= { cRC 4 }

		
		-- 1.3.6.1.4.1.19338.19.2.1.24
		cUSTXTRF OBJECT-IDENTITY
			STATUS current
			DESCRIPTION 
				"Description."
			::= { network1 24 }

		
		-- 1.3.6.1.4.1.19338.19.2.1.24.1
		totalINCount24 OBJECT-TYPE
			SYNTAX OCTET STRING
			MAX-ACCESS read-write
			STATUS current
			DESCRIPTION
				"Description."
			::= { cUSTXTRF 1 }

		
		-- 1.3.6.1.4.1.19338.19.2.1.24.2
		successCount24 OBJECT-TYPE
			SYNTAX OCTET STRING
			MAX-ACCESS read-write
			STATUS current
			DESCRIPTION
				"Description."
			::= { cUSTXTRF 2 }

		
		-- 1.3.6.1.4.1.19338.19.2.1.24.3
		failCount24 OBJECT-TYPE
			SYNTAX OCTET STRING
			MAX-ACCESS read-write
			STATUS current
			DESCRIPTION
				"Description."
			::= { cUSTXTRF 3 }

		
		-- 1.3.6.1.4.1.19338.19.2.1.24.4
		refusedCount24 OBJECT-TYPE
			SYNTAX OCTET STRING
			MAX-ACCESS read-write
			STATUS current
			DESCRIPTION
				"Description."
			::= { cUSTXTRF 4 }

		
		-- 1.3.6.1.4.1.19338.19.2.1.25
		dELREGSUBS OBJECT-IDENTITY
			STATUS current
			DESCRIPTION 
				"Description."
			::= { network1 25 }

		
		-- 1.3.6.1.4.1.19338.19.2.1.25.1
		totalINCount25 OBJECT-TYPE
			SYNTAX OCTET STRING
			MAX-ACCESS read-write
			STATUS current
			DESCRIPTION
				"Description."
			::= { dELREGSUBS 1 }

		
		-- 1.3.6.1.4.1.19338.19.2.1.25.2
		successCount25 OBJECT-TYPE
			SYNTAX OCTET STRING
			MAX-ACCESS read-write
			STATUS current
			DESCRIPTION
				"Description."
			::= { dELREGSUBS 2 }

		
		-- 1.3.6.1.4.1.19338.19.2.1.25.3
		failCount25 OBJECT-TYPE
			SYNTAX OCTET STRING
			MAX-ACCESS read-write
			STATUS current
			DESCRIPTION
				"Description."
			::= { dELREGSUBS 3 }

		
		-- 1.3.6.1.4.1.19338.19.2.1.25.4
		refusedCount25 OBJECT-TYPE
			SYNTAX OCTET STRING
			MAX-ACCESS read-write
			STATUS current
			DESCRIPTION
				"Description."
			::= { dELREGSUBS 4 }

		
		-- 1.3.6.1.4.1.19338.19.2.1.26
		dELSID OBJECT-IDENTITY
			STATUS current
			DESCRIPTION 
				"Description."
			::= { network1 26 }

		
		-- 1.3.6.1.4.1.19338.19.2.1.26.1
		totalINCount26 OBJECT-TYPE
			SYNTAX OCTET STRING
			MAX-ACCESS read-write
			STATUS current
			DESCRIPTION
				"Description."
			::= { dELSID 1 }

		
		-- 1.3.6.1.4.1.19338.19.2.1.26.2
		successCount26 OBJECT-TYPE
			SYNTAX OCTET STRING
			MAX-ACCESS read-write
			STATUS current
			DESCRIPTION
				"Description."
			::= { dELSID 2 }

		
		-- 1.3.6.1.4.1.19338.19.2.1.26.3
		failCount26 OBJECT-TYPE
			SYNTAX OCTET STRING
			MAX-ACCESS read-write
			STATUS current
			DESCRIPTION
				"Description."
			::= { dELSID 3 }

		
		-- 1.3.6.1.4.1.19338.19.2.1.26.4
		refusedCount26 OBJECT-TYPE
			SYNTAX OCTET STRING
			MAX-ACCESS read-write
			STATUS current
			DESCRIPTION
				"Description."
			::= { dELSID 4 }

		
		-- 1.3.6.1.4.1.19338.19.2.1.27
		dRCRTRF OBJECT-IDENTITY
			STATUS current
			DESCRIPTION 
				"Description."
			::= { network1 27 }

		
		-- 1.3.6.1.4.1.19338.19.2.1.27.1
		totalINCount27 OBJECT-TYPE
			SYNTAX OCTET STRING
			MAX-ACCESS read-write
			STATUS current
			DESCRIPTION
				"Description."
			::= { dRCRTRF 1 }

		
		-- 1.3.6.1.4.1.19338.19.2.1.27.2
		successCount27 OBJECT-TYPE
			SYNTAX OCTET STRING
			MAX-ACCESS read-write
			STATUS current
			DESCRIPTION
				"Description."
			::= { dRCRTRF 2 }

		
		-- 1.3.6.1.4.1.19338.19.2.1.27.3
		failCount27 OBJECT-TYPE
			SYNTAX OCTET STRING
			MAX-ACCESS read-write
			STATUS current
			DESCRIPTION
				"Description."
			::= { dRCRTRF 3 }

		
		-- 1.3.6.1.4.1.19338.19.2.1.27.4
		refusedCount27 OBJECT-TYPE
			SYNTAX OCTET STRING
			MAX-ACCESS read-write
			STATUS current
			DESCRIPTION
				"Description."
			::= { dRCRTRF 4 }

		
		-- 1.3.6.1.4.1.19338.19.2.1.28
		eNQSID OBJECT-IDENTITY
			STATUS current
			DESCRIPTION 
				"Description."
			::= { network1 28 }

		
		-- 1.3.6.1.4.1.19338.19.2.1.28.1
		totalINCount28 OBJECT-TYPE
			SYNTAX OCTET STRING
			MAX-ACCESS read-write
			STATUS current
			DESCRIPTION
				"Description."
			::= { eNQSID 1 }

		
		-- 1.3.6.1.4.1.19338.19.2.1.28.2
		successCount28 OBJECT-TYPE
			SYNTAX OCTET STRING
			MAX-ACCESS read-write
			STATUS current
			DESCRIPTION
				"Description."
			::= { eNQSID 2 }

		
		-- 1.3.6.1.4.1.19338.19.2.1.28.3
		failCount28 OBJECT-TYPE
			SYNTAX OCTET STRING
			MAX-ACCESS read-write
			STATUS current
			DESCRIPTION
				"Description."
			::= { eNQSID 3 }

		
		-- 1.3.6.1.4.1.19338.19.2.1.28.4
		refusedCount28 OBJECT-TYPE
			SYNTAX OCTET STRING
			MAX-ACCESS read-write
			STATUS current
			DESCRIPTION
				"Description."
			::= { eNQSID 4 }

		
		-- 1.3.6.1.4.1.19338.19.2.1.29
		eVD OBJECT-IDENTITY
			STATUS current
			DESCRIPTION 
				"Description."
			::= { network1 29 }

		
		-- 1.3.6.1.4.1.19338.19.2.1.29.1
		totalINCount29 OBJECT-TYPE
			SYNTAX OCTET STRING
			MAX-ACCESS read-write
			STATUS current
			DESCRIPTION
				"Description."
			::= { eVD 1 }

		
		-- 1.3.6.1.4.1.19338.19.2.1.29.2
		successCount29 OBJECT-TYPE
			SYNTAX OCTET STRING
			MAX-ACCESS read-write
			STATUS current
			DESCRIPTION
				"Description."
			::= { eVD 2 }

		
		-- 1.3.6.1.4.1.19338.19.2.1.29.3
		failCount29 OBJECT-TYPE
			SYNTAX OCTET STRING
			MAX-ACCESS read-write
			STATUS current
			DESCRIPTION
				"Description."
			::= { eVD 3 }

		
		-- 1.3.6.1.4.1.19338.19.2.1.29.4
		refusedCount29 OBJECT-TYPE
			SYNTAX OCTET STRING
			MAX-ACCESS read-write
			STATUS current
			DESCRIPTION
				"Description."
			::= { eVD 4 }

		
		-- 1.3.6.1.4.1.19338.19.2.1.30
		eVR OBJECT-IDENTITY
			STATUS current
			DESCRIPTION 
				"Description."
			::= { network1 30 }

		
		-- 1.3.6.1.4.1.19338.19.2.1.30.1
		totalINCount30 OBJECT-TYPE
			SYNTAX OCTET STRING
			MAX-ACCESS read-write
			STATUS current
			DESCRIPTION
				"Description."
			::= { eVR 1 }

		
		-- 1.3.6.1.4.1.19338.19.2.1.30.2
		successCount30 OBJECT-TYPE
			SYNTAX OCTET STRING
			MAX-ACCESS read-write
			STATUS current
			DESCRIPTION
				"Description."
			::= { eVR 2 }

		
		-- 1.3.6.1.4.1.19338.19.2.1.30.3
		failCount30 OBJECT-TYPE
			SYNTAX OCTET STRING
			MAX-ACCESS read-write
			STATUS current
			DESCRIPTION
				"Description."
			::= { eVR 3 }

		
		-- 1.3.6.1.4.1.19338.19.2.1.30.4
		refusedCount30 OBJECT-TYPE
			SYNTAX OCTET STRING
			MAX-ACCESS read-write
			STATUS current
			DESCRIPTION
				"Description."
			::= { eVR 4 }

		
		-- 1.3.6.1.4.1.19338.19.2.1.31
		eXTGRPH OBJECT-IDENTITY
			STATUS current
			DESCRIPTION 
				"Description."
			::= { network1 31 }

		
		-- 1.3.6.1.4.1.19338.19.2.1.31.1
		totalINCount31 OBJECT-TYPE
			SYNTAX OCTET STRING
			MAX-ACCESS read-write
			STATUS current
			DESCRIPTION
				"Description."
			::= { eXTGRPH 1 }

		
		-- 1.3.6.1.4.1.19338.19.2.1.31.2
		successCount31 OBJECT-TYPE
			SYNTAX OCTET STRING
			MAX-ACCESS read-write
			STATUS current
			DESCRIPTION
				"Description."
			::= { eXTGRPH 2 }

		
		-- 1.3.6.1.4.1.19338.19.2.1.31.3
		failCount31 OBJECT-TYPE
			SYNTAX OCTET STRING
			MAX-ACCESS read-write
			STATUS current
			DESCRIPTION
				"Description."
			::= { eXTGRPH 3 }

		
		-- 1.3.6.1.4.1.19338.19.2.1.31.4
		refusedCount31 OBJECT-TYPE
			SYNTAX OCTET STRING
			MAX-ACCESS read-write
			STATUS current
			DESCRIPTION
				"Description."
			::= { eXTGRPH 4 }

		
		-- 1.3.6.1.4.1.19338.19.2.1.32
		eXTSUSRES OBJECT-IDENTITY
			STATUS current
			DESCRIPTION 
				"Description."
			::= { network1 32 }

		
		-- 1.3.6.1.4.1.19338.19.2.1.32.1
		totalINCount32 OBJECT-TYPE
			SYNTAX OCTET STRING
			MAX-ACCESS read-write
			STATUS current
			DESCRIPTION
				"Description."
			::= { eXTSUSRES 1 }

		
		-- 1.3.6.1.4.1.19338.19.2.1.32.2
		successCount32 OBJECT-TYPE
			SYNTAX OCTET STRING
			MAX-ACCESS read-write
			STATUS current
			DESCRIPTION
				"Description."
			::= { eXTSUSRES 2 }

		
		-- 1.3.6.1.4.1.19338.19.2.1.32.3
		failCount32 OBJECT-TYPE
			SYNTAX OCTET STRING
			MAX-ACCESS read-write
			STATUS current
			DESCRIPTION
				"Description."
			::= { eXTSUSRES 3 }

		
		-- 1.3.6.1.4.1.19338.19.2.1.32.4
		refusedCount32 OBJECT-TYPE
			SYNTAX OCTET STRING
			MAX-ACCESS read-write
			STATUS current
			DESCRIPTION
				"Description."
			::= { eXTSUSRES 4 }

		
		-- 1.3.6.1.4.1.19338.19.2.1.33
		eXTUSRADD OBJECT-IDENTITY
			STATUS current
			DESCRIPTION 
				"Description."
			::= { network1 33 }

		
		-- 1.3.6.1.4.1.19338.19.2.1.33.1
		totalINCount33 OBJECT-TYPE
			SYNTAX OCTET STRING
			MAX-ACCESS read-write
			STATUS current
			DESCRIPTION
				"Description."
			::= { eXTUSRADD 1 }

		
		-- 1.3.6.1.4.1.19338.19.2.1.33.2
		successCount33 OBJECT-TYPE
			SYNTAX OCTET STRING
			MAX-ACCESS read-write
			STATUS current
			DESCRIPTION
				"Description."
			::= { eXTUSRADD 2 }

		
		-- 1.3.6.1.4.1.19338.19.2.1.33.3
		failCount33 OBJECT-TYPE
			SYNTAX OCTET STRING
			MAX-ACCESS read-write
			STATUS current
			DESCRIPTION
				"Description."
			::= { eXTUSRADD 3 }

		
		-- 1.3.6.1.4.1.19338.19.2.1.33.4
		refusedCount33 OBJECT-TYPE
			SYNTAX OCTET STRING
			MAX-ACCESS read-write
			STATUS current
			DESCRIPTION
				"Description."
			::= { eXTUSRADD 4 }

		
		-- 1.3.6.1.4.1.19338.19.2.1.34
		iCCIDMSISD OBJECT-IDENTITY
			STATUS current
			DESCRIPTION 
				"Description."
			::= { network1 34 }

		
		-- 1.3.6.1.4.1.19338.19.2.1.34.1
		totalINCount34 OBJECT-TYPE
			SYNTAX OCTET STRING
			MAX-ACCESS read-write
			STATUS current
			DESCRIPTION
				"Description."
			::= { iCCIDMSISD 1 }

		
		-- 1.3.6.1.4.1.19338.19.2.1.34.2
		successCount34 OBJECT-TYPE
			SYNTAX OCTET STRING
			MAX-ACCESS read-write
			STATUS current
			DESCRIPTION
				"Description."
			::= { iCCIDMSISD 2 }

		
		-- 1.3.6.1.4.1.19338.19.2.1.34.3
		failCount34 OBJECT-TYPE
			SYNTAX OCTET STRING
			MAX-ACCESS read-write
			STATUS current
			DESCRIPTION
				"Description."
			::= { iCCIDMSISD 3 }

		
		-- 1.3.6.1.4.1.19338.19.2.1.34.4
		refusedCount34 OBJECT-TYPE
			SYNTAX OCTET STRING
			MAX-ACCESS read-write
			STATUS current
			DESCRIPTION
				"Description."
			::= { iCCIDMSISD 4 }

		
		-- 1.3.6.1.4.1.19338.19.2.1.35
		iNENQREQ OBJECT-IDENTITY
			STATUS current
			DESCRIPTION 
				"Description."
			::= { network1 35 }

		
		-- 1.3.6.1.4.1.19338.19.2.1.35.1
		totalINCount35 OBJECT-TYPE
			SYNTAX OCTET STRING
			MAX-ACCESS read-write
			STATUS current
			DESCRIPTION
				"Description."
			::= { iNENQREQ 1 }

		
		-- 1.3.6.1.4.1.19338.19.2.1.35.2
		successCount35 OBJECT-TYPE
			SYNTAX OCTET STRING
			MAX-ACCESS read-write
			STATUS current
			DESCRIPTION
				"Description."
			::= { iNENQREQ 2 }

		
		-- 1.3.6.1.4.1.19338.19.2.1.35.3
		failCount35 OBJECT-TYPE
			SYNTAX OCTET STRING
			MAX-ACCESS read-write
			STATUS current
			DESCRIPTION
				"Description."
			::= { iNENQREQ 3 }

		
		-- 1.3.6.1.4.1.19338.19.2.1.35.4
		refusedCount35 OBJECT-TYPE
			SYNTAX OCTET STRING
			MAX-ACCESS read-write
			STATUS current
			DESCRIPTION
				"Description."
			::= { iNENQREQ 4 }

		
		-- 1.3.6.1.4.1.19338.19.2.1.36
		iNTRRC OBJECT-IDENTITY
			STATUS current
			DESCRIPTION 
				"Description."
			::= { network1 36 }

		
		-- 1.3.6.1.4.1.19338.19.2.1.36.1
		totalINCount36 OBJECT-TYPE
			SYNTAX OCTET STRING
			MAX-ACCESS read-write
			STATUS current
			DESCRIPTION
				"Description."
			::= { iNTRRC 1 }

		
		-- 1.3.6.1.4.1.19338.19.2.1.36.2
		successCount36 OBJECT-TYPE
			SYNTAX OCTET STRING
			MAX-ACCESS read-write
			STATUS current
			DESCRIPTION
				"Description."
			::= { iNTRRC 2 }

		
		-- 1.3.6.1.4.1.19338.19.2.1.36.3
		failCount36 OBJECT-TYPE
			SYNTAX OCTET STRING
			MAX-ACCESS read-write
			STATUS current
			DESCRIPTION
				"Description."
			::= { iNTRRC 3 }

		
		-- 1.3.6.1.4.1.19338.19.2.1.36.4
		refusedCount36 OBJECT-TYPE
			SYNTAX OCTET STRING
			MAX-ACCESS read-write
			STATUS current
			DESCRIPTION
				"Description."
			::= { iNTRRC 4 }

		
		-- 1.3.6.1.4.1.19338.19.2.1.37
		iR OBJECT-IDENTITY
			STATUS current
			DESCRIPTION 
				"Description."
			::= { network1 37 }

		
		-- 1.3.6.1.4.1.19338.19.2.1.37.1
		totalINCount37 OBJECT-TYPE
			SYNTAX OCTET STRING
			MAX-ACCESS read-write
			STATUS current
			DESCRIPTION
				"Description."
			::= { iR 1 }

		
		-- 1.3.6.1.4.1.19338.19.2.1.37.2
		successCount37 OBJECT-TYPE
			SYNTAX OCTET STRING
			MAX-ACCESS read-write
			STATUS current
			DESCRIPTION
				"Description."
			::= { iR 2 }

		
		-- 1.3.6.1.4.1.19338.19.2.1.37.3
		failCount37 OBJECT-TYPE
			SYNTAX OCTET STRING
			MAX-ACCESS read-write
			STATUS current
			DESCRIPTION
				"Description."
			::= { iR 3 }

		
		-- 1.3.6.1.4.1.19338.19.2.1.37.4
		refusedCount37 OBJECT-TYPE
			SYNTAX OCTET STRING
			MAX-ACCESS read-write
			STATUS current
			DESCRIPTION
				"Description."
			::= { iR 4 }

		
		-- 1.3.6.1.4.1.19338.19.2.1.38
		lASTXTRF OBJECT-IDENTITY
			STATUS current
			DESCRIPTION 
				"Description."
			::= { network1 38 }

		
		-- 1.3.6.1.4.1.19338.19.2.1.38.1
		totalINCount38 OBJECT-TYPE
			SYNTAX OCTET STRING
			MAX-ACCESS read-write
			STATUS current
			DESCRIPTION
				"Description."
			::= { lASTXTRF 1 }

		
		-- 1.3.6.1.4.1.19338.19.2.1.38.2
		successCount38 OBJECT-TYPE
			SYNTAX OCTET STRING
			MAX-ACCESS read-write
			STATUS current
			DESCRIPTION
				"Description."
			::= { lASTXTRF 2 }

		
		-- 1.3.6.1.4.1.19338.19.2.1.38.3
		failCount38 OBJECT-TYPE
			SYNTAX OCTET STRING
			MAX-ACCESS read-write
			STATUS current
			DESCRIPTION
				"Description."
			::= { lASTXTRF 3 }

		
		-- 1.3.6.1.4.1.19338.19.2.1.38.4
		refusedCount38 OBJECT-TYPE
			SYNTAX OCTET STRING
			MAX-ACCESS read-write
			STATUS current
			DESCRIPTION
				"Description."
			::= { lASTXTRF 4 }

		
		-- 1.3.6.1.4.1.19338.19.2.1.39
		lMBDBT OBJECT-IDENTITY
			STATUS current
			DESCRIPTION 
				"Description."
			::= { network1 39 }

		
		-- 1.3.6.1.4.1.19338.19.2.1.39.1
		totalINCount39 OBJECT-TYPE
			SYNTAX OCTET STRING
			MAX-ACCESS read-write
			STATUS current
			DESCRIPTION
				"Description."
			::= { lMBDBT 1 }

		
		-- 1.3.6.1.4.1.19338.19.2.1.39.2
		successCount39 OBJECT-TYPE
			SYNTAX OCTET STRING
			MAX-ACCESS read-write
			STATUS current
			DESCRIPTION
				"Description."
			::= { lMBDBT 2 }

		
		-- 1.3.6.1.4.1.19338.19.2.1.39.3
		failCount39 OBJECT-TYPE
			SYNTAX OCTET STRING
			MAX-ACCESS read-write
			STATUS current
			DESCRIPTION
				"Description."
			::= { lMBDBT 3 }

		
		-- 1.3.6.1.4.1.19338.19.2.1.39.4
		refusedCount39 OBJECT-TYPE
			SYNTAX OCTET STRING
			MAX-ACCESS read-write
			STATUS current
			DESCRIPTION
				"Description."
			::= { lMBDBT 4 }

		
		-- 1.3.6.1.4.1.19338.19.2.1.40
		mCDL OBJECT-IDENTITY
			STATUS current
			DESCRIPTION 
				"Description."
			::= { network1 40 }

		
		-- 1.3.6.1.4.1.19338.19.2.1.40.1
		totalINCount40 OBJECT-TYPE
			SYNTAX OCTET STRING
			MAX-ACCESS read-write
			STATUS current
			DESCRIPTION
				"Description."
			::= { mCDL 1 }

		
		-- 1.3.6.1.4.1.19338.19.2.1.40.2
		successCount40 OBJECT-TYPE
			SYNTAX OCTET STRING
			MAX-ACCESS read-write
			STATUS current
			DESCRIPTION
				"Description."
			::= { mCDL 2 }

		
		-- 1.3.6.1.4.1.19338.19.2.1.40.3
		failCount40 OBJECT-TYPE
			SYNTAX OCTET STRING
			MAX-ACCESS read-write
			STATUS current
			DESCRIPTION
				"Description."
			::= { mCDL 3 }

		
		-- 1.3.6.1.4.1.19338.19.2.1.40.4
		refusedCount40 OBJECT-TYPE
			SYNTAX OCTET STRING
			MAX-ACCESS read-write
			STATUS current
			DESCRIPTION
				"Description."
			::= { mCDL 4 }

		
		-- 1.3.6.1.4.1.19338.19.2.1.41
		mCDLR OBJECT-IDENTITY
			STATUS current
			DESCRIPTION 
				"Description."
			::= { network1 41 }

		
		-- 1.3.6.1.4.1.19338.19.2.1.41.1
		totalINCount41 OBJECT-TYPE
			SYNTAX OCTET STRING
			MAX-ACCESS read-write
			STATUS current
			DESCRIPTION
				"Description."
			::= { mCDLR 1 }

		
		-- 1.3.6.1.4.1.19338.19.2.1.41.2
		successCount41 OBJECT-TYPE
			SYNTAX OCTET STRING
			MAX-ACCESS read-write
			STATUS current
			DESCRIPTION
				"Description."
			::= { mCDLR 2 }

		
		-- 1.3.6.1.4.1.19338.19.2.1.41.3
		failCount41 OBJECT-TYPE
			SYNTAX OCTET STRING
			MAX-ACCESS read-write
			STATUS current
			DESCRIPTION
				"Description."
			::= { mCDLR 3 }

		
		-- 1.3.6.1.4.1.19338.19.2.1.41.4
		refusedCount41 OBJECT-TYPE
			SYNTAX OCTET STRING
			MAX-ACCESS read-write
			STATUS current
			DESCRIPTION
				"Description."
			::= { mCDLR 4 }

		
		-- 1.3.6.1.4.1.19338.19.2.1.42
		mCDLV OBJECT-IDENTITY
			STATUS current
			DESCRIPTION 
				"Description."
			::= { network1 42 }

		
		-- 1.3.6.1.4.1.19338.19.2.1.42.1
		totalINCount42 OBJECT-TYPE
			SYNTAX OCTET STRING
			MAX-ACCESS read-write
			STATUS current
			DESCRIPTION
				"Description."
			::= { mCDLV 1 }

		
		-- 1.3.6.1.4.1.19338.19.2.1.42.2
		successCount42 OBJECT-TYPE
			SYNTAX OCTET STRING
			MAX-ACCESS read-write
			STATUS current
			DESCRIPTION
				"Description."
			::= { mCDLV 2 }

		
		-- 1.3.6.1.4.1.19338.19.2.1.42.3
		failCount42 OBJECT-TYPE
			SYNTAX OCTET STRING
			MAX-ACCESS read-write
			STATUS current
			DESCRIPTION
				"Description."
			::= { mCDLV 3 }

		
		-- 1.3.6.1.4.1.19338.19.2.1.42.4
		refusedCount42 OBJECT-TYPE
			SYNTAX OCTET STRING
			MAX-ACCESS read-write
			STATUS current
			DESCRIPTION
				"Description."
			::= { mCDLV 4 }

		
		-- 1.3.6.1.4.1.19338.19.2.1.43
		mNPUPLOAD OBJECT-IDENTITY
			STATUS current
			DESCRIPTION 
				"Description."
			::= { network1 43 }

		
		-- 1.3.6.1.4.1.19338.19.2.1.43.1
		totalINCount43 OBJECT-TYPE
			SYNTAX OCTET STRING
			MAX-ACCESS read-write
			STATUS current
			DESCRIPTION
				"Description."
			::= { mNPUPLOAD 1 }

		
		-- 1.3.6.1.4.1.19338.19.2.1.43.2
		successCount43 OBJECT-TYPE
			SYNTAX OCTET STRING
			MAX-ACCESS read-write
			STATUS current
			DESCRIPTION
				"Description."
			::= { mNPUPLOAD 2 }

		
		-- 1.3.6.1.4.1.19338.19.2.1.43.3
		failCount43 OBJECT-TYPE
			SYNTAX OCTET STRING
			MAX-ACCESS read-write
			STATUS current
			DESCRIPTION
				"Description."
			::= { mNPUPLOAD 3 }

		
		-- 1.3.6.1.4.1.19338.19.2.1.43.4
		refusedCount43 OBJECT-TYPE
			SYNTAX OCTET STRING
			MAX-ACCESS read-write
			STATUS current
			DESCRIPTION
				"Description."
			::= { mNPUPLOAD 4 }

		
		-- 1.3.6.1.4.1.19338.19.2.1.44
		multDEL OBJECT-IDENTITY
			STATUS current
			DESCRIPTION 
				"Description."
			::= { network1 44 }

		
		-- 1.3.6.1.4.1.19338.19.2.1.44.1
		totalINCount44 OBJECT-TYPE
			SYNTAX OCTET STRING
			MAX-ACCESS read-write
			STATUS current
			DESCRIPTION
				"Description."
			::= { multDEL 1 }

		
		-- 1.3.6.1.4.1.19338.19.2.1.44.2
		successCount44 OBJECT-TYPE
			SYNTAX OCTET STRING
			MAX-ACCESS read-write
			STATUS current
			DESCRIPTION
				"Description."
			::= { multDEL 2 }

		
		-- 1.3.6.1.4.1.19338.19.2.1.44.3
		failCount44 OBJECT-TYPE
			SYNTAX OCTET STRING
			MAX-ACCESS read-write
			STATUS current
			DESCRIPTION
				"Description."
			::= { multDEL 3 }

		
		-- 1.3.6.1.4.1.19338.19.2.1.44.4
		refusedCount44 OBJECT-TYPE
			SYNTAX OCTET STRING
			MAX-ACCESS read-write
			STATUS current
			DESCRIPTION
				"Description."
			::= { multDEL 4 }

		
		-- 1.3.6.1.4.1.19338.19.2.1.45
		mvd OBJECT-IDENTITY
			STATUS current
			DESCRIPTION 
				"Description."
			::= { network1 45 }

		
		-- 1.3.6.1.4.1.19338.19.2.1.45.1
		totalINCount45 OBJECT-TYPE
			SYNTAX OCTET STRING
			MAX-ACCESS read-write
			STATUS current
			DESCRIPTION
				"Description."
			::= { mvd 1 }

		
		-- 1.3.6.1.4.1.19338.19.2.1.45.2
		successCount45 OBJECT-TYPE
			SYNTAX OCTET STRING
			MAX-ACCESS read-write
			STATUS current
			DESCRIPTION
				"Description."
			::= { mvd 2 }

		
		-- 1.3.6.1.4.1.19338.19.2.1.45.3
		failCount45 OBJECT-TYPE
			SYNTAX OCTET STRING
			MAX-ACCESS read-write
			STATUS current
			DESCRIPTION
				"Description."
			::= { mvd 3 }

		
		-- 1.3.6.1.4.1.19338.19.2.1.45.4
		refusedCount45 OBJECT-TYPE
			SYNTAX OCTET STRING
			MAX-ACCESS read-write
			STATUS current
			DESCRIPTION
				"Description."
			::= { mvd 4 }

		
		-- 1.3.6.1.4.1.19338.19.2.1.46
		o2cIN OBJECT-IDENTITY
			STATUS current
			DESCRIPTION 
				"Description."
			::= { network1 46 }

		
		-- 1.3.6.1.4.1.19338.19.2.1.46.1
		totalINCount46 OBJECT-TYPE
			SYNTAX OCTET STRING
			MAX-ACCESS read-write
			STATUS current
			DESCRIPTION
				"Description."
			::= { o2cIN 1 }

		
		-- 1.3.6.1.4.1.19338.19.2.1.46.2
		successCount46 OBJECT-TYPE
			SYNTAX OCTET STRING
			MAX-ACCESS read-write
			STATUS current
			DESCRIPTION
				"Description."
			::= { o2cIN 2 }

		
		-- 1.3.6.1.4.1.19338.19.2.1.46.3
		failCount46 OBJECT-TYPE
			SYNTAX OCTET STRING
			MAX-ACCESS read-write
			STATUS current
			DESCRIPTION
				"Description."
			::= { o2cIN 3 }

		
		-- 1.3.6.1.4.1.19338.19.2.1.46.4
		refusedCount46 OBJECT-TYPE
			SYNTAX OCTET STRING
			MAX-ACCESS read-write
			STATUS current
			DESCRIPTION
				"Description."
			::= { o2cIN 4 }

		
		-- 1.3.6.1.4.1.19338.19.2.1.47
		o2cINTR OBJECT-IDENTITY
			STATUS current
			DESCRIPTION 
				"Description."
			::= { network1 47 }

		
		-- 1.3.6.1.4.1.19338.19.2.1.47.1
		totalINCount47 OBJECT-TYPE
			SYNTAX OCTET STRING
			MAX-ACCESS read-write
			STATUS current
			DESCRIPTION
				"Description."
			::= { o2cINTR 1 }

		
		-- 1.3.6.1.4.1.19338.19.2.1.47.2
		successCount47 OBJECT-TYPE
			SYNTAX OCTET STRING
			MAX-ACCESS read-write
			STATUS current
			DESCRIPTION
				"Description."
			::= { o2cINTR 2 }

		
		-- 1.3.6.1.4.1.19338.19.2.1.47.3
		failCount47 OBJECT-TYPE
			SYNTAX OCTET STRING
			MAX-ACCESS read-write
			STATUS current
			DESCRIPTION
				"Description."
			::= { o2cINTR 3 }

		
		-- 1.3.6.1.4.1.19338.19.2.1.47.4
		refusedCount47 OBJECT-TYPE
			SYNTAX OCTET STRING
			MAX-ACCESS read-write
			STATUS current
			DESCRIPTION
				"Description."
			::= { o2cINTR 4 }

		
		-- 1.3.6.1.4.1.19338.19.2.1.48
		o2cRET OBJECT-IDENTITY
			STATUS current
			DESCRIPTION 
				"Description."
			::= { network1 48 }

		
		-- 1.3.6.1.4.1.19338.19.2.1.48.1
		totalINCount48 OBJECT-TYPE
			SYNTAX OCTET STRING
			MAX-ACCESS read-write
			STATUS current
			DESCRIPTION
				"Description."
			::= { o2cRET 1 }

		
		-- 1.3.6.1.4.1.19338.19.2.1.48.2
		successCount48 OBJECT-TYPE
			SYNTAX OCTET STRING
			MAX-ACCESS read-write
			STATUS current
			DESCRIPTION
				"Description."
			::= { o2cRET 2 }

		
		-- 1.3.6.1.4.1.19338.19.2.1.48.3
		failCount48 OBJECT-TYPE
			SYNTAX OCTET STRING
			MAX-ACCESS read-write
			STATUS current
			DESCRIPTION
				"Description."
			::= { o2cRET 3 }

		
		-- 1.3.6.1.4.1.19338.19.2.1.48.4
		refusedCount48 OBJECT-TYPE
			SYNTAX OCTET STRING
			MAX-ACCESS read-write
			STATUS current
			DESCRIPTION
				"Description."
			::= { o2cRET 4 }

		
		-- 1.3.6.1.4.1.19338.19.2.1.49
		o2cWD OBJECT-IDENTITY
			STATUS current
			DESCRIPTION 
				"Description."
			::= { network1 49 }

		
		-- 1.3.6.1.4.1.19338.19.2.1.49.1
		totalINCount49 OBJECT-TYPE
			SYNTAX OCTET STRING
			MAX-ACCESS read-write
			STATUS current
			DESCRIPTION
				"Description."
			::= { o2cWD 1 }

		
		-- 1.3.6.1.4.1.19338.19.2.1.49.2
		successCount49 OBJECT-TYPE
			SYNTAX OCTET STRING
			MAX-ACCESS read-write
			STATUS current
			DESCRIPTION
				"Description."
			::= { o2cWD 2 }

		
		-- 1.3.6.1.4.1.19338.19.2.1.49.3
		failCount49 OBJECT-TYPE
			SYNTAX OCTET STRING
			MAX-ACCESS read-write
			STATUS current
			DESCRIPTION
				"Description."
			::= { o2cWD 3 }

		
		-- 1.3.6.1.4.1.19338.19.2.1.49.4
		refusedCount49 OBJECT-TYPE
			SYNTAX OCTET STRING
			MAX-ACCESS read-write
			STATUS current
			DESCRIPTION
				"Description."
			::= { o2cWD 4 }

		
		-- 1.3.6.1.4.1.19338.19.2.1.50
		ordc OBJECT-IDENTITY
			STATUS current
			DESCRIPTION 
				"Description."
			::= { network1 50 }

		
		-- 1.3.6.1.4.1.19338.19.2.1.50.1
		totalINCount50 OBJECT-TYPE
			SYNTAX OCTET STRING
			MAX-ACCESS read-write
			STATUS current
			DESCRIPTION
				"Description."
			::= { ordc 1 }

		
		-- 1.3.6.1.4.1.19338.19.2.1.50.2
		successCount50 OBJECT-TYPE
			SYNTAX OCTET STRING
			MAX-ACCESS read-write
			STATUS current
			DESCRIPTION
				"Description."
			::= { ordc 2 }

		
		-- 1.3.6.1.4.1.19338.19.2.1.50.3
		failCount50 OBJECT-TYPE
			SYNTAX OCTET STRING
			MAX-ACCESS read-write
			STATUS current
			DESCRIPTION
				"Description."
			::= { ordc 3 }

		
		-- 1.3.6.1.4.1.19338.19.2.1.50.4
		refusedCount50 OBJECT-TYPE
			SYNTAX OCTET STRING
			MAX-ACCESS read-write
			STATUS current
			DESCRIPTION
				"Description."
			::= { ordc 4 }

		
		-- 1.3.6.1.4.1.19338.19.2.1.51
		ordl OBJECT-IDENTITY
			STATUS current
			DESCRIPTION 
				"Description."
			::= { network1 51 }

		
		-- 1.3.6.1.4.1.19338.19.2.1.51.1
		totalINCount51 OBJECT-TYPE
			SYNTAX OCTET STRING
			MAX-ACCESS read-write
			STATUS current
			DESCRIPTION
				"Description."
			::= { ordl 1 }

		
		-- 1.3.6.1.4.1.19338.19.2.1.51.2
		successCount51 OBJECT-TYPE
			SYNTAX OCTET STRING
			MAX-ACCESS read-write
			STATUS current
			DESCRIPTION
				"Description."
			::= { ordl 2 }

		
		-- 1.3.6.1.4.1.19338.19.2.1.51.3
		failCount51 OBJECT-TYPE
			SYNTAX OCTET STRING
			MAX-ACCESS read-write
			STATUS current
			DESCRIPTION
				"Description."
			::= { ordl 3 }

		
		-- 1.3.6.1.4.1.19338.19.2.1.51.4
		refusedCount51 OBJECT-TYPE
			SYNTAX OCTET STRING
			MAX-ACCESS read-write
			STATUS current
			DESCRIPTION
				"Description."
			::= { ordl 4 }

		
		-- 1.3.6.1.4.1.19338.19.2.1.52
		otherBALAN OBJECT-IDENTITY
			STATUS current
			DESCRIPTION 
				"Description."
			::= { network1 52 }

		
		-- 1.3.6.1.4.1.19338.19.2.1.52.1
		totalINCount52 OBJECT-TYPE
			SYNTAX OCTET STRING
			MAX-ACCESS read-write
			STATUS current
			DESCRIPTION
				"Description."
			::= { otherBALAN 1 }

		
		-- 1.3.6.1.4.1.19338.19.2.1.52.2
		successCount52 OBJECT-TYPE
			SYNTAX OCTET STRING
			MAX-ACCESS read-write
			STATUS current
			DESCRIPTION
				"Description."
			::= { otherBALAN 2 }

		
		-- 1.3.6.1.4.1.19338.19.2.1.52.3
		failCount52 OBJECT-TYPE
			SYNTAX OCTET STRING
			MAX-ACCESS read-write
			STATUS current
			DESCRIPTION
				"Description."
			::= { otherBALAN 3 }

		
		-- 1.3.6.1.4.1.19338.19.2.1.52.4
		refusedCount52 OBJECT-TYPE
			SYNTAX OCTET STRING
			MAX-ACCESS read-write
			STATUS current
			DESCRIPTION
				"Description."
			::= { otherBALAN 4 }

		
		-- 1.3.6.1.4.1.19338.19.2.1.53
		p2pENQ1 OBJECT-IDENTITY
			STATUS current
			DESCRIPTION 
				"Description."
			::= { network1 53 }

		
		-- 1.3.6.1.4.1.19338.19.2.1.53.1
		totalINCount53 OBJECT-TYPE
			SYNTAX OCTET STRING
			MAX-ACCESS read-write
			STATUS current
			DESCRIPTION
				"Description."
			::= { p2pENQ1 1 }

		
		-- 1.3.6.1.4.1.19338.19.2.1.53.2
		successCount53 OBJECT-TYPE
			SYNTAX OCTET STRING
			MAX-ACCESS read-write
			STATUS current
			DESCRIPTION
				"Description."
			::= { p2pENQ1 2 }

		
		-- 1.3.6.1.4.1.19338.19.2.1.53.3
		failCount53 OBJECT-TYPE
			SYNTAX OCTET STRING
			MAX-ACCESS read-write
			STATUS current
			DESCRIPTION
				"Description."
			::= { p2pENQ1 3 }

		
		-- 1.3.6.1.4.1.19338.19.2.1.53.4
		refusedCount53 OBJECT-TYPE
			SYNTAX OCTET STRING
			MAX-ACCESS read-write
			STATUS current
			DESCRIPTION
				"Description."
			::= { p2pENQ1 4 }

		
		-- 1.3.6.1.4.1.19338.19.2.1.54
		p2pENQ2 OBJECT-IDENTITY
			STATUS current
			DESCRIPTION 
				"Description."
			::= { network1 54 }

		
		-- 1.3.6.1.4.1.19338.19.2.1.54.1
		totalINCount54 OBJECT-TYPE
			SYNTAX OCTET STRING
			MAX-ACCESS read-write
			STATUS current
			DESCRIPTION
				"Description."
			::= { p2pENQ2 1 }

		
		-- 1.3.6.1.4.1.19338.19.2.1.54.2
		successCount54 OBJECT-TYPE
			SYNTAX OCTET STRING
			MAX-ACCESS read-write
			STATUS current
			DESCRIPTION
				"Description."
			::= { p2pENQ2 2 }

		
		-- 1.3.6.1.4.1.19338.19.2.1.54.3
		failCount54 OBJECT-TYPE
			SYNTAX OCTET STRING
			MAX-ACCESS read-write
			STATUS current
			DESCRIPTION
				"Description."
			::= { p2pENQ2 3 }

		
		-- 1.3.6.1.4.1.19338.19.2.1.54.4
		refusedCount54 OBJECT-TYPE
			SYNTAX OCTET STRING
			MAX-ACCESS read-write
			STATUS current
			DESCRIPTION
				"Description."
			::= { p2pENQ2 4 }

		
		-- 1.3.6.1.4.1.19338.19.2.1.55
		pACCST OBJECT-IDENTITY
			STATUS current
			DESCRIPTION 
				"Description."
			::= { network1 55 }

		
		-- 1.3.6.1.4.1.19338.19.2.1.55.1
		totalINCount55 OBJECT-TYPE
			SYNTAX OCTET STRING
			MAX-ACCESS read-write
			STATUS current
			DESCRIPTION
				"Description."
			::= { pACCST 1 }

		
		-- 1.3.6.1.4.1.19338.19.2.1.55.2
		successCount55 OBJECT-TYPE
			SYNTAX OCTET STRING
			MAX-ACCESS read-write
			STATUS current
			DESCRIPTION
				"Description."
			::= { pACCST 2 }

		
		-- 1.3.6.1.4.1.19338.19.2.1.55.3
		failCount55 OBJECT-TYPE
			SYNTAX OCTET STRING
			MAX-ACCESS read-write
			STATUS current
			DESCRIPTION
				"Description."
			::= { pACCST 3 }

		
		-- 1.3.6.1.4.1.19338.19.2.1.55.4
		refusedCount55 OBJECT-TYPE
			SYNTAX OCTET STRING
			MAX-ACCESS read-write
			STATUS current
			DESCRIPTION
				"Description."
			::= { pACCST 4 }

		
		-- 1.3.6.1.4.1.19338.19.2.1.56
		pADD OBJECT-IDENTITY
			STATUS current
			DESCRIPTION 
				"Description."
			::= { network1 56 }

		
		-- 1.3.6.1.4.1.19338.19.2.1.56.1
		totalINCount56 OBJECT-TYPE
			SYNTAX OCTET STRING
			MAX-ACCESS read-write
			STATUS current
			DESCRIPTION
				"Description."
			::= { pADD 1 }

		
		-- 1.3.6.1.4.1.19338.19.2.1.56.2
		successCount56 OBJECT-TYPE
			SYNTAX OCTET STRING
			MAX-ACCESS read-write
			STATUS current
			DESCRIPTION
				"Description."
			::= { pADD 2 }

		
		-- 1.3.6.1.4.1.19338.19.2.1.56.3
		failCount56 OBJECT-TYPE
			SYNTAX OCTET STRING
			MAX-ACCESS read-write
			STATUS current
			DESCRIPTION
				"Description."
			::= { pADD 3 }

		
		-- 1.3.6.1.4.1.19338.19.2.1.56.4
		refusedCount56 OBJECT-TYPE
			SYNTAX OCTET STRING
			MAX-ACCESS read-write
			STATUS current
			DESCRIPTION
				"Description."
			::= { pADD 4 }

		
		-- 1.3.6.1.4.1.19338.19.2.1.57
		pBAR OBJECT-IDENTITY
			STATUS current
			DESCRIPTION 
				"Description."
			::= { network1 57 }

		
		-- 1.3.6.1.4.1.19338.19.2.1.57.1
		totalINCount57 OBJECT-TYPE
			SYNTAX OCTET STRING
			MAX-ACCESS read-write
			STATUS current
			DESCRIPTION
				"Description."
			::= { pBAR 1 }

		
		-- 1.3.6.1.4.1.19338.19.2.1.57.2
		successCount57 OBJECT-TYPE
			SYNTAX OCTET STRING
			MAX-ACCESS read-write
			STATUS current
			DESCRIPTION
				"Description."
			::= { pBAR 2 }

		
		-- 1.3.6.1.4.1.19338.19.2.1.57.3
		failCount57 OBJECT-TYPE
			SYNTAX OCTET STRING
			MAX-ACCESS read-write
			STATUS current
			DESCRIPTION
				"Description."
			::= { pBAR 3 }

		
		-- 1.3.6.1.4.1.19338.19.2.1.57.4
		refusedCount57 OBJECT-TYPE
			SYNTAX OCTET STRING
			MAX-ACCESS read-write
			STATUS current
			DESCRIPTION
				"Description."
			::= { pBAR 4 }

		
		-- 1.3.6.1.4.1.19338.19.2.1.58
		pCHLAN OBJECT-IDENTITY
			STATUS current
			DESCRIPTION 
				"Description."
			::= { network1 58 }

		
		-- 1.3.6.1.4.1.19338.19.2.1.58.1
		totalINCount58 OBJECT-TYPE
			SYNTAX OCTET STRING
			MAX-ACCESS read-write
			STATUS current
			DESCRIPTION
				"Description."
			::= { pCHLAN 1 }

		
		-- 1.3.6.1.4.1.19338.19.2.1.58.2
		successCount58 OBJECT-TYPE
			SYNTAX OCTET STRING
			MAX-ACCESS read-write
			STATUS current
			DESCRIPTION
				"Description."
			::= { pCHLAN 2 }

		
		-- 1.3.6.1.4.1.19338.19.2.1.58.3
		failCount58 OBJECT-TYPE
			SYNTAX OCTET STRING
			MAX-ACCESS read-write
			STATUS current
			DESCRIPTION
				"Description."
			::= { pCHLAN 3 }

		
		-- 1.3.6.1.4.1.19338.19.2.1.58.4
		refusedCount58 OBJECT-TYPE
			SYNTAX OCTET STRING
			MAX-ACCESS read-write
			STATUS current
			DESCRIPTION
				"Description."
			::= { pCHLAN 4 }

		
		-- 1.3.6.1.4.1.19338.19.2.1.59
		pCNF OBJECT-IDENTITY
			STATUS current
			DESCRIPTION 
				"Description."
			::= { network1 59 }

		
		-- 1.3.6.1.4.1.19338.19.2.1.59.1
		totalINCount59 OBJECT-TYPE
			SYNTAX OCTET STRING
			MAX-ACCESS read-write
			STATUS current
			DESCRIPTION
				"Description."
			::= { pCNF 1 }

		
		-- 1.3.6.1.4.1.19338.19.2.1.59.2
		successCount59 OBJECT-TYPE
			SYNTAX OCTET STRING
			MAX-ACCESS read-write
			STATUS current
			DESCRIPTION
				"Description."
			::= { pCNF 2 }

		
		-- 1.3.6.1.4.1.19338.19.2.1.59.3
		failCount59 OBJECT-TYPE
			SYNTAX OCTET STRING
			MAX-ACCESS read-write
			STATUS current
			DESCRIPTION
				"Description."
			::= { pCNF 3 }

		
		-- 1.3.6.1.4.1.19338.19.2.1.59.4
		refusedCount59 OBJECT-TYPE
			SYNTAX OCTET STRING
			MAX-ACCESS read-write
			STATUS current
			DESCRIPTION
				"Description."
			::= { pCNF 4 }

		
		-- 1.3.6.1.4.1.19338.19.2.1.60
		pcr OBJECT-IDENTITY
			STATUS current
			DESCRIPTION 
				"Description."
			::= { network1 60 }

		
		-- 1.3.6.1.4.1.19338.19.2.1.60.1
		totalINCount60 OBJECT-TYPE
			SYNTAX OCTET STRING
			MAX-ACCESS read-write
			STATUS current
			DESCRIPTION
				"Description."
			::= { pcr 1 }

		
		-- 1.3.6.1.4.1.19338.19.2.1.60.2
		successCount60 OBJECT-TYPE
			SYNTAX OCTET STRING
			MAX-ACCESS read-write
			STATUS current
			DESCRIPTION
				"Description."
			::= { pcr 2 }

		
		-- 1.3.6.1.4.1.19338.19.2.1.60.3
		failCount60 OBJECT-TYPE
			SYNTAX OCTET STRING
			MAX-ACCESS read-write
			STATUS current
			DESCRIPTION
				"Description."
			::= { pcr 3 }

		
		-- 1.3.6.1.4.1.19338.19.2.1.60.4
		refusedCount60 OBJECT-TYPE
			SYNTAX OCTET STRING
			MAX-ACCESS read-write
			STATUS current
			DESCRIPTION
				"Description."
			::= { pcr 4 }

		
		-- 1.3.6.1.4.1.19338.19.2.1.61
		pDEL OBJECT-IDENTITY
			STATUS current
			DESCRIPTION 
				"Description."
			::= { network1 61 }

		
		-- 1.3.6.1.4.1.19338.19.2.1.61.1
		totalINCount61 OBJECT-TYPE
			SYNTAX OCTET STRING
			MAX-ACCESS read-write
			STATUS current
			DESCRIPTION
				"Description."
			::= { pDEL 1 }

		
		-- 1.3.6.1.4.1.19338.19.2.1.61.2
		successCount61 OBJECT-TYPE
			SYNTAX OCTET STRING
			MAX-ACCESS read-write
			STATUS current
			DESCRIPTION
				"Description."
			::= { pDEL 2 }

		
		-- 1.3.6.1.4.1.19338.19.2.1.61.3
		failCount61 OBJECT-TYPE
			SYNTAX OCTET STRING
			MAX-ACCESS read-write
			STATUS current
			DESCRIPTION
				"Description."
			::= { pDEL 3 }

		
		-- 1.3.6.1.4.1.19338.19.2.1.61.4
		refusedCount61 OBJECT-TYPE
			SYNTAX OCTET STRING
			MAX-ACCESS read-write
			STATUS current
			DESCRIPTION
				"Description."
			::= { pDEL 4 }

		
		-- 1.3.6.1.4.1.19338.19.2.1.62
		pdREG OBJECT-IDENTITY
			STATUS current
			DESCRIPTION 
				"Description."
			::= { network1 62 }

		
		-- 1.3.6.1.4.1.19338.19.2.1.62.1
		totalINCount62 OBJECT-TYPE
			SYNTAX OCTET STRING
			MAX-ACCESS read-write
			STATUS current
			DESCRIPTION
				"Description."
			::= { pdREG 1 }

		
		-- 1.3.6.1.4.1.19338.19.2.1.62.2
		successCount62 OBJECT-TYPE
			SYNTAX OCTET STRING
			MAX-ACCESS read-write
			STATUS current
			DESCRIPTION
				"Description."
			::= { pdREG 2 }

		
		-- 1.3.6.1.4.1.19338.19.2.1.62.3
		failCount62 OBJECT-TYPE
			SYNTAX OCTET STRING
			MAX-ACCESS read-write
			STATUS current
			DESCRIPTION
				"Description."
			::= { pdREG 3 }

		
		-- 1.3.6.1.4.1.19338.19.2.1.62.4
		refusedCount62 OBJECT-TYPE
			SYNTAX OCTET STRING
			MAX-ACCESS read-write
			STATUS current
			DESCRIPTION
				"Description."
			::= { pdREG 4 }

		
		-- 1.3.6.1.4.1.19338.19.2.1.63
		pList OBJECT-IDENTITY
			STATUS current
			DESCRIPTION 
				"Description."
			::= { network1 63 }

		
		-- 1.3.6.1.4.1.19338.19.2.1.63.1
		totalINCount63 OBJECT-TYPE
			SYNTAX OCTET STRING
			MAX-ACCESS read-write
			STATUS current
			DESCRIPTION
				"Description."
			::= { pList 1 }

		
		-- 1.3.6.1.4.1.19338.19.2.1.63.2
		successCount63 OBJECT-TYPE
			SYNTAX OCTET STRING
			MAX-ACCESS read-write
			STATUS current
			DESCRIPTION
				"Description."
			::= { pList 2 }

		
		-- 1.3.6.1.4.1.19338.19.2.1.63.3
		failCount63 OBJECT-TYPE
			SYNTAX OCTET STRING
			MAX-ACCESS read-write
			STATUS current
			DESCRIPTION
				"Description."
			::= { pList 3 }

		
		-- 1.3.6.1.4.1.19338.19.2.1.63.4
		refusedCount63 OBJECT-TYPE
			SYNTAX OCTET STRING
			MAX-ACCESS read-write
			STATUS current
			DESCRIPTION
				"Description."
			::= { pList 4 }

		
		-- 1.3.6.1.4.1.19338.19.2.1.64
		plt OBJECT-IDENTITY
			STATUS current
			DESCRIPTION 
				"Description."
			::= { network1 64 }

		
		-- 1.3.6.1.4.1.19338.19.2.1.64.1
		totalINCount64 OBJECT-TYPE
			SYNTAX OCTET STRING
			MAX-ACCESS read-write
			STATUS current
			DESCRIPTION
				"Description."
			::= { plt 1 }

		
		-- 1.3.6.1.4.1.19338.19.2.1.64.2
		successCount64 OBJECT-TYPE
			SYNTAX OCTET STRING
			MAX-ACCESS read-write
			STATUS current
			DESCRIPTION
				"Description."
			::= { plt 2 }

		
		-- 1.3.6.1.4.1.19338.19.2.1.64.3
		failCount64 OBJECT-TYPE
			SYNTAX OCTET STRING
			MAX-ACCESS read-write
			STATUS current
			DESCRIPTION
				"Description."
			::= { plt 3 }

		
		-- 1.3.6.1.4.1.19338.19.2.1.64.4
		refusedCount64 OBJECT-TYPE
			SYNTAX OCTET STRING
			MAX-ACCESS read-write
			STATUS current
			DESCRIPTION
				"Description."
			::= { plt 4 }

		
		-- 1.3.6.1.4.1.19338.19.2.1.65
		ppb OBJECT-IDENTITY
			STATUS current
			DESCRIPTION 
				"Description."
			::= { network1 65 }

		
		-- 1.3.6.1.4.1.19338.19.2.1.65.1
		totalINCount65 OBJECT-TYPE
			SYNTAX OCTET STRING
			MAX-ACCESS read-write
			STATUS current
			DESCRIPTION
				"Description."
			::= { ppb 1 }

		
		-- 1.3.6.1.4.1.19338.19.2.1.65.2
		successCount65 OBJECT-TYPE
			SYNTAX OCTET STRING
			MAX-ACCESS read-write
			STATUS current
			DESCRIPTION
				"Description."
			::= { ppb 2 }

		
		-- 1.3.6.1.4.1.19338.19.2.1.65.3
		failCount65 OBJECT-TYPE
			SYNTAX OCTET STRING
			MAX-ACCESS read-write
			STATUS current
			DESCRIPTION
				"Description."
			::= { ppb 3 }

		
		-- 1.3.6.1.4.1.19338.19.2.1.65.4
		refusedCount65 OBJECT-TYPE
			SYNTAX OCTET STRING
			MAX-ACCESS read-write
			STATUS current
			DESCRIPTION
				"Description."
			::= { ppb 4 }

		
		-- 1.3.6.1.4.1.19338.19.2.1.66
		ppel OBJECT-IDENTITY
			STATUS current
			DESCRIPTION 
				"Description."
			::= { network1 66 }

		
		-- 1.3.6.1.4.1.19338.19.2.1.66.1
		totalINCount66 OBJECT-TYPE
			SYNTAX OCTET STRING
			MAX-ACCESS read-write
			STATUS current
			DESCRIPTION
				"Description."
			::= { ppel 1 }

		
		-- 1.3.6.1.4.1.19338.19.2.1.66.2
		successCount66 OBJECT-TYPE
			SYNTAX OCTET STRING
			MAX-ACCESS read-write
			STATUS current
			DESCRIPTION
				"Description."
			::= { ppel 2 }

		
		-- 1.3.6.1.4.1.19338.19.2.1.66.3
		failCount66 OBJECT-TYPE
			SYNTAX OCTET STRING
			MAX-ACCESS read-write
			STATUS current
			DESCRIPTION
				"Description."
			::= { ppel 3 }

		
		-- 1.3.6.1.4.1.19338.19.2.1.66.4
		refusedCount66 OBJECT-TYPE
			SYNTAX OCTET STRING
			MAX-ACCESS read-write
			STATUS current
			DESCRIPTION
				"Description."
			::= { ppel 4 }

		
		-- 1.3.6.1.4.1.19338.19.2.1.67
		pr OBJECT-IDENTITY
			STATUS current
			DESCRIPTION 
				"Description."
			::= { network1 67 }

		
		-- 1.3.6.1.4.1.19338.19.2.1.67.1
		totalINCount67 OBJECT-TYPE
			SYNTAX OCTET STRING
			MAX-ACCESS read-write
			STATUS current
			DESCRIPTION
				"Description."
			::= { pr 1 }

		
		-- 1.3.6.1.4.1.19338.19.2.1.67.2
		successCount67 OBJECT-TYPE
			SYNTAX OCTET STRING
			MAX-ACCESS read-write
			STATUS current
			DESCRIPTION
				"Description."
			::= { pr 2 }

		
		-- 1.3.6.1.4.1.19338.19.2.1.67.3
		failCount67 OBJECT-TYPE
			SYNTAX OCTET STRING
			MAX-ACCESS read-write
			STATUS current
			DESCRIPTION
				"Description."
			::= { pr 3 }

		
		-- 1.3.6.1.4.1.19338.19.2.1.67.4
		refusedCount67 OBJECT-TYPE
			SYNTAX OCTET STRING
			MAX-ACCESS read-write
			STATUS current
			DESCRIPTION
				"Description."
			::= { pr 4 }

		
		-- 1.3.6.1.4.1.19338.19.2.1.68
		prc OBJECT-IDENTITY
			STATUS current
			DESCRIPTION 
				"Description."
			::= { network1 68 }

		
		-- 1.3.6.1.4.1.19338.19.2.1.68.1
		totalINCount68 OBJECT-TYPE
			SYNTAX OCTET STRING
			MAX-ACCESS read-write
			STATUS current
			DESCRIPTION
				"Description."
			::= { prc 1 }

		
		-- 1.3.6.1.4.1.19338.19.2.1.68.2
		successCount68 OBJECT-TYPE
			SYNTAX OCTET STRING
			MAX-ACCESS read-write
			STATUS current
			DESCRIPTION
				"Description."
			::= { prc 2 }

		
		-- 1.3.6.1.4.1.19338.19.2.1.68.3
		failCount68 OBJECT-TYPE
			SYNTAX OCTET STRING
			MAX-ACCESS read-write
			STATUS current
			DESCRIPTION
				"Description."
			::= { prc 3 }

		
		-- 1.3.6.1.4.1.19338.19.2.1.68.4
		refusedCount68 OBJECT-TYPE
			SYNTAX OCTET STRING
			MAX-ACCESS read-write
			STATUS current
			DESCRIPTION
				"Description."
			::= { prc 4 }

		
		-- 1.3.6.1.4.1.19338.19.2.1.69
		pRCMDA OBJECT-IDENTITY
			STATUS current
			DESCRIPTION 
				"Description."
			::= { network1 69 }

		
		-- 1.3.6.1.4.1.19338.19.2.1.69.1
		totalINCount69 OBJECT-TYPE
			SYNTAX OCTET STRING
			MAX-ACCESS read-write
			STATUS current
			DESCRIPTION
				"Description."
			::= { pRCMDA 1 }

		
		-- 1.3.6.1.4.1.19338.19.2.1.69.2
		successCount69 OBJECT-TYPE
			SYNTAX OCTET STRING
			MAX-ACCESS read-write
			STATUS current
			DESCRIPTION
				"Description."
			::= { pRCMDA 2 }

		
		-- 1.3.6.1.4.1.19338.19.2.1.69.3
		failCount69 OBJECT-TYPE
			SYNTAX OCTET STRING
			MAX-ACCESS read-write
			STATUS current
			DESCRIPTION
				"Description."
			::= { pRCMDA 3 }

		
		-- 1.3.6.1.4.1.19338.19.2.1.69.4
		refusedCount69 OBJECT-TYPE
			SYNTAX OCTET STRING
			MAX-ACCESS read-write
			STATUS current
			DESCRIPTION
				"Description."
			::= { pRCMDA 4 }

		
		-- 1.3.6.1.4.1.19338.19.2.1.70
		preg OBJECT-IDENTITY
			STATUS current
			DESCRIPTION 
				"Description."
			::= { network1 70 }

		
		-- 1.3.6.1.4.1.19338.19.2.1.70.1
		totalINCount70 OBJECT-TYPE
			SYNTAX OCTET STRING
			MAX-ACCESS read-write
			STATUS current
			DESCRIPTION
				"Description."
			::= { preg 1 }

		
		-- 1.3.6.1.4.1.19338.19.2.1.70.2
		successCount70 OBJECT-TYPE
			SYNTAX OCTET STRING
			MAX-ACCESS read-write
			STATUS current
			DESCRIPTION
				"Description."
			::= { preg 2 }

		
		-- 1.3.6.1.4.1.19338.19.2.1.70.3
		failCount70 OBJECT-TYPE
			SYNTAX OCTET STRING
			MAX-ACCESS read-write
			STATUS current
			DESCRIPTION
				"Description."
			::= { preg 3 }

		
		-- 1.3.6.1.4.1.19338.19.2.1.70.4
		refusedCount70 OBJECT-TYPE
			SYNTAX OCTET STRING
			MAX-ACCESS read-write
			STATUS current
			DESCRIPTION
				"Description."
			::= { preg 4 }

		
		-- 1.3.6.1.4.1.19338.19.2.1.71
		pres OBJECT-IDENTITY
			STATUS current
			DESCRIPTION 
				"Description."
			::= { network1 71 }

		
		-- 1.3.6.1.4.1.19338.19.2.1.71.1
		totalINCount71 OBJECT-TYPE
			SYNTAX OCTET STRING
			MAX-ACCESS read-write
			STATUS current
			DESCRIPTION
				"Description."
			::= { pres 1 }

		
		-- 1.3.6.1.4.1.19338.19.2.1.71.2
		successCount71 OBJECT-TYPE
			SYNTAX OCTET STRING
			MAX-ACCESS read-write
			STATUS current
			DESCRIPTION
				"Description."
			::= { pres 2 }

		
		-- 1.3.6.1.4.1.19338.19.2.1.71.3
		failCount71 OBJECT-TYPE
			SYNTAX OCTET STRING
			MAX-ACCESS read-write
			STATUS current
			DESCRIPTION
				"Description."
			::= { pres 3 }

		
		-- 1.3.6.1.4.1.19338.19.2.1.71.4
		refusedCount71 OBJECT-TYPE
			SYNTAX OCTET STRING
			MAX-ACCESS read-write
			STATUS current
			DESCRIPTION
				"Description."
			::= { pres 4 }

		
		-- 1.3.6.1.4.1.19338.19.2.1.72
		ps OBJECT-IDENTITY
			STATUS current
			DESCRIPTION 
				"Description."
			::= { network1 72 }

		
		-- 1.3.6.1.4.1.19338.19.2.1.72.1
		totalINCount72 OBJECT-TYPE
			SYNTAX OCTET STRING
			MAX-ACCESS read-write
			STATUS current
			DESCRIPTION
				"Description."
			::= { ps 1 }

		
		-- 1.3.6.1.4.1.19338.19.2.1.72.2
		successCount72 OBJECT-TYPE
			SYNTAX OCTET STRING
			MAX-ACCESS read-write
			STATUS current
			DESCRIPTION
				"Description."
			::= { ps 2 }

		
		-- 1.3.6.1.4.1.19338.19.2.1.72.3
		failCount72 OBJECT-TYPE
			SYNTAX OCTET STRING
			MAX-ACCESS read-write
			STATUS current
			DESCRIPTION
				"Description."
			::= { ps 3 }

		
		-- 1.3.6.1.4.1.19338.19.2.1.72.4
		refusedCount72 OBJECT-TYPE
			SYNTAX OCTET STRING
			MAX-ACCESS read-write
			STATUS current
			DESCRIPTION
				"Description."
			::= { ps 4 }

		
		-- 1.3.6.1.4.1.19338.19.2.1.73
		pSTNRC OBJECT-IDENTITY
			STATUS current
			DESCRIPTION 
				"Description."
			::= { network1 73 }

		
		-- 1.3.6.1.4.1.19338.19.2.1.73.1
		totalINCount73 OBJECT-TYPE
			SYNTAX OCTET STRING
			MAX-ACCESS read-write
			STATUS current
			DESCRIPTION
				"Description."
			::= { pSTNRC 1 }

		
		-- 1.3.6.1.4.1.19338.19.2.1.73.2
		successCount73 OBJECT-TYPE
			SYNTAX OCTET STRING
			MAX-ACCESS read-write
			STATUS current
			DESCRIPTION
				"Description."
			::= { pSTNRC 2 }

		
		-- 1.3.6.1.4.1.19338.19.2.1.73.3
		failCount73 OBJECT-TYPE
			SYNTAX OCTET STRING
			MAX-ACCESS read-write
			STATUS current
			DESCRIPTION
				"Description."
			::= { pSTNRC 3 }

		
		-- 1.3.6.1.4.1.19338.19.2.1.73.4
		refusedCount73 OBJECT-TYPE
			SYNTAX OCTET STRING
			MAX-ACCESS read-write
			STATUS current
			DESCRIPTION
				"Description."
			::= { pSTNRC 4 }

		
		-- 1.3.6.1.4.1.19338.19.2.1.74
		pSUS OBJECT-IDENTITY
			STATUS current
			DESCRIPTION 
				"Description."
			::= { network1 74 }

		
		-- 1.3.6.1.4.1.19338.19.2.1.74.1
		totalINCount74 OBJECT-TYPE
			SYNTAX OCTET STRING
			MAX-ACCESS read-write
			STATUS current
			DESCRIPTION
				"Description."
			::= { pSUS 1 }

		
		-- 1.3.6.1.4.1.19338.19.2.1.74.2
		successCount74 OBJECT-TYPE
			SYNTAX OCTET STRING
			MAX-ACCESS read-write
			STATUS current
			DESCRIPTION
				"Description."
			::= { pSUS 2 }

		
		-- 1.3.6.1.4.1.19338.19.2.1.74.3
		failCount74 OBJECT-TYPE
			SYNTAX OCTET STRING
			MAX-ACCESS read-write
			STATUS current
			DESCRIPTION
				"Description."
			::= { pSUS 3 }

		
		-- 1.3.6.1.4.1.19338.19.2.1.74.4
		refusedCount74 OBJECT-TYPE
			SYNTAX OCTET STRING
			MAX-ACCESS read-write
			STATUS current
			DESCRIPTION
				"Description."
			::= { pSUS 4 }

		
		-- 1.3.6.1.4.1.19338.19.2.1.75
		ptr OBJECT-IDENTITY
			STATUS current
			DESCRIPTION 
				"Description."
			::= { network1 75 }

		
		-- 1.3.6.1.4.1.19338.19.2.1.75.1
		totalINCount75 OBJECT-TYPE
			SYNTAX OCTET STRING
			MAX-ACCESS read-write
			STATUS current
			DESCRIPTION
				"Description."
			::= { ptr 1 }

		
		-- 1.3.6.1.4.1.19338.19.2.1.75.2
		successCount75 OBJECT-TYPE
			SYNTAX OCTET STRING
			MAX-ACCESS read-write
			STATUS current
			DESCRIPTION
				"Description."
			::= { ptr 2 }

		
		-- 1.3.6.1.4.1.19338.19.2.1.75.3
		failCount75 OBJECT-TYPE
			SYNTAX OCTET STRING
			MAX-ACCESS read-write
			STATUS current
			DESCRIPTION
				"Description."
			::= { ptr 3 }

		
		-- 1.3.6.1.4.1.19338.19.2.1.75.4
		refusedCount75 OBJECT-TYPE
			SYNTAX OCTET STRING
			MAX-ACCESS read-write
			STATUS current
			DESCRIPTION
				"Description."
			::= { ptr 4 }

		
		-- 1.3.6.1.4.1.19338.19.2.1.76
		pVAS OBJECT-IDENTITY
			STATUS current
			DESCRIPTION 
				"Description."
			::= { network1 76 }

		
		-- 1.3.6.1.4.1.19338.19.2.1.76.1
		totalINCount76 OBJECT-TYPE
			SYNTAX OCTET STRING
			MAX-ACCESS read-write
			STATUS current
			DESCRIPTION
				"Description."
			::= { pVAS 1 }

		
		-- 1.3.6.1.4.1.19338.19.2.1.76.2
		successCount76 OBJECT-TYPE
			SYNTAX OCTET STRING
			MAX-ACCESS read-write
			STATUS current
			DESCRIPTION
				"Description."
			::= { pVAS 2 }

		
		-- 1.3.6.1.4.1.19338.19.2.1.76.3
		failCount76 OBJECT-TYPE
			SYNTAX OCTET STRING
			MAX-ACCESS read-write
			STATUS current
			DESCRIPTION
				"Description."
			::= { pVAS 3 }

		
		-- 1.3.6.1.4.1.19338.19.2.1.76.4
		refusedCount76 OBJECT-TYPE
			SYNTAX OCTET STRING
			MAX-ACCESS read-write
			STATUS current
			DESCRIPTION
				"Description."
			::= { pVAS 4 }

		
		-- 1.3.6.1.4.1.19338.19.2.1.77
		rc OBJECT-IDENTITY
			STATUS current
			DESCRIPTION 
				"Description."
			::= { network1 77 }

		
		-- 1.3.6.1.4.1.19338.19.2.1.77.1
		totalINCount77 OBJECT-TYPE
			SYNTAX OCTET STRING
			MAX-ACCESS read-write
			STATUS current
			DESCRIPTION
				"Description."
			::= { rc 1 }

		
		-- 1.3.6.1.4.1.19338.19.2.1.77.2
		successCount77 OBJECT-TYPE
			SYNTAX OCTET STRING
			MAX-ACCESS read-write
			STATUS current
			DESCRIPTION
				"Description."
			::= { rc 2 }

		
		-- 1.3.6.1.4.1.19338.19.2.1.77.3
		failCount77 OBJECT-TYPE
			SYNTAX OCTET STRING
			MAX-ACCESS read-write
			STATUS current
			DESCRIPTION
				"Description."
			::= { rc 3 }

		
		-- 1.3.6.1.4.1.19338.19.2.1.77.4
		refusedCount77 OBJECT-TYPE
			SYNTAX OCTET STRING
			MAX-ACCESS read-write
			STATUS current
			DESCRIPTION
				"Description."
			::= { rc 4 }

		
		-- 1.3.6.1.4.1.19338.19.2.1.78
		rce OBJECT-IDENTITY
			STATUS current
			DESCRIPTION 
				"Description."
			::= { network1 78 }

		
		-- 1.3.6.1.4.1.19338.19.2.1.78.1
		totalINCount78 OBJECT-TYPE
			SYNTAX OCTET STRING
			MAX-ACCESS read-write
			STATUS current
			DESCRIPTION
				"Description."
			::= { rce 1 }

		
		-- 1.3.6.1.4.1.19338.19.2.1.78.2
		successCount78 OBJECT-TYPE
			SYNTAX OCTET STRING
			MAX-ACCESS read-write
			STATUS current
			DESCRIPTION
				"Description."
			::= { rce 2 }

		
		-- 1.3.6.1.4.1.19338.19.2.1.78.3
		failCount78 OBJECT-TYPE
			SYNTAX OCTET STRING
			MAX-ACCESS read-write
			STATUS current
			DESCRIPTION
				"Description."
			::= { rce 3 }

		
		-- 1.3.6.1.4.1.19338.19.2.1.78.4
		refusedCount78 OBJECT-TYPE
			SYNTAX OCTET STRING
			MAX-ACCESS read-write
			STATUS current
			DESCRIPTION
				"Description."
			::= { rce 4 }

		
		-- 1.3.6.1.4.1.19338.19.2.1.79
		regSID OBJECT-IDENTITY
			STATUS current
			DESCRIPTION 
				"Description."
			::= { network1 79 }

		
		-- 1.3.6.1.4.1.19338.19.2.1.79.1
		totalINCount79 OBJECT-TYPE
			SYNTAX OCTET STRING
			MAX-ACCESS read-write
			STATUS current
			DESCRIPTION
				"Description."
			::= { regSID 1 }

		
		-- 1.3.6.1.4.1.19338.19.2.1.79.2
		successCount79 OBJECT-TYPE
			SYNTAX OCTET STRING
			MAX-ACCESS read-write
			STATUS current
			DESCRIPTION
				"Description."
			::= { regSID 2 }

		
		-- 1.3.6.1.4.1.19338.19.2.1.79.3
		failCount79 OBJECT-TYPE
			SYNTAX OCTET STRING
			MAX-ACCESS read-write
			STATUS current
			DESCRIPTION
				"Description."
			::= { regSID 3 }

		
		-- 1.3.6.1.4.1.19338.19.2.1.79.4
		refusedCount79 OBJECT-TYPE
			SYNTAX OCTET STRING
			MAX-ACCESS read-write
			STATUS current
			DESCRIPTION
				"Description."
			::= { regSID 4 }

		
		-- 1.3.6.1.4.1.19338.19.2.1.80
		resP2PSER OBJECT-IDENTITY
			STATUS current
			DESCRIPTION 
				"Description."
			::= { network1 80 }

		
		-- 1.3.6.1.4.1.19338.19.2.1.80.1
		totalINCount80 OBJECT-TYPE
			SYNTAX OCTET STRING
			MAX-ACCESS read-write
			STATUS current
			DESCRIPTION
				"Description."
			::= { resP2PSER 1 }

		
		-- 1.3.6.1.4.1.19338.19.2.1.80.2
		successCount80 OBJECT-TYPE
			SYNTAX OCTET STRING
			MAX-ACCESS read-write
			STATUS current
			DESCRIPTION
				"Description."
			::= { resP2PSER 2 }

		
		-- 1.3.6.1.4.1.19338.19.2.1.80.3
		failCount80 OBJECT-TYPE
			SYNTAX OCTET STRING
			MAX-ACCESS read-write
			STATUS current
			DESCRIPTION
				"Description."
			::= { resP2PSER 3 }

		
		-- 1.3.6.1.4.1.19338.19.2.1.80.4
		refusedCount80 OBJECT-TYPE
			SYNTAX OCTET STRING
			MAX-ACCESS read-write
			STATUS current
			DESCRIPTION
				"Description."
			::= { resP2PSER 4 }

		
		-- 1.3.6.1.4.1.19338.19.2.1.81
		ret OBJECT-IDENTITY
			STATUS current
			DESCRIPTION 
				"Description."
			::= { network1 81 }

		
		-- 1.3.6.1.4.1.19338.19.2.1.81.1
		totalINCount81 OBJECT-TYPE
			SYNTAX OCTET STRING
			MAX-ACCESS read-write
			STATUS current
			DESCRIPTION
				"Description."
			::= { ret 1 }

		
		-- 1.3.6.1.4.1.19338.19.2.1.81.2
		successCount81 OBJECT-TYPE
			SYNTAX OCTET STRING
			MAX-ACCESS read-write
			STATUS current
			DESCRIPTION
				"Description."
			::= { ret 2 }

		
		-- 1.3.6.1.4.1.19338.19.2.1.81.3
		failCount81 OBJECT-TYPE
			SYNTAX OCTET STRING
			MAX-ACCESS read-write
			STATUS current
			DESCRIPTION
				"Description."
			::= { ret 3 }

		
		-- 1.3.6.1.4.1.19338.19.2.1.81.4
		refusedCount81 OBJECT-TYPE
			SYNTAX OCTET STRING
			MAX-ACCESS read-write
			STATUS current
			DESCRIPTION
				"Description."
			::= { ret 4 }

		
		-- 1.3.6.1.4.1.19338.19.2.1.82
		rr OBJECT-IDENTITY
			STATUS current
			DESCRIPTION 
				"Description."
			::= { network1 82 }

		
		-- 1.3.6.1.4.1.19338.19.2.1.82.1
		totalINCount82 OBJECT-TYPE
			SYNTAX OCTET STRING
			MAX-ACCESS read-write
			STATUS current
			DESCRIPTION
				"Description."
			::= { rr 1 }

		
		-- 1.3.6.1.4.1.19338.19.2.1.82.2
		successCount82 OBJECT-TYPE
			SYNTAX OCTET STRING
			MAX-ACCESS read-write
			STATUS current
			DESCRIPTION
				"Description."
			::= { rr 2 }

		
		-- 1.3.6.1.4.1.19338.19.2.1.82.3
		failCount82 OBJECT-TYPE
			SYNTAX OCTET STRING
			MAX-ACCESS read-write
			STATUS current
			DESCRIPTION
				"Description."
			::= { rr 3 }

		
		-- 1.3.6.1.4.1.19338.19.2.1.82.4
		refusedCount82 OBJECT-TYPE
			SYNTAX OCTET STRING
			MAX-ACCESS read-write
			STATUS current
			DESCRIPTION
				"Description."
			::= { rr 4 }

		
		-- 1.3.6.1.4.1.19338.19.2.1.83
		rs OBJECT-IDENTITY
			STATUS current
			DESCRIPTION 
				"Description."
			::= { network1 83 }

		
		-- 1.3.6.1.4.1.19338.19.2.1.83.1
		totalINCount83 OBJECT-TYPE
			SYNTAX OCTET STRING
			MAX-ACCESS read-write
			STATUS current
			DESCRIPTION
				"Description."
			::= { rs 1 }

		
		-- 1.3.6.1.4.1.19338.19.2.1.83.2
		successCount83 OBJECT-TYPE
			SYNTAX OCTET STRING
			MAX-ACCESS read-write
			STATUS current
			DESCRIPTION
				"Description."
			::= { rs 2 }

		
		-- 1.3.6.1.4.1.19338.19.2.1.83.3
		failCount83 OBJECT-TYPE
			SYNTAX OCTET STRING
			MAX-ACCESS read-write
			STATUS current
			DESCRIPTION
				"Description."
			::= { rs 3 }

		
		-- 1.3.6.1.4.1.19338.19.2.1.83.4
		refusedCount83 OBJECT-TYPE
			SYNTAX OCTET STRING
			MAX-ACCESS read-write
			STATUS current
			DESCRIPTION
				"Description."
			::= { rs 4 }

		
		-- 1.3.6.1.4.1.19338.19.2.1.84
		rub OBJECT-IDENTITY
			STATUS current
			DESCRIPTION 
				"Description."
			::= { network1 84 }

		
		-- 1.3.6.1.4.1.19338.19.2.1.84.1
		totalINCount84 OBJECT-TYPE
			SYNTAX OCTET STRING
			MAX-ACCESS read-write
			STATUS current
			DESCRIPTION
				"Description."
			::= { rub 1 }

		
		-- 1.3.6.1.4.1.19338.19.2.1.84.2
		successCount84 OBJECT-TYPE
			SYNTAX OCTET STRING
			MAX-ACCESS read-write
			STATUS current
			DESCRIPTION
				"Description."
			::= { rub 2 }

		
		-- 1.3.6.1.4.1.19338.19.2.1.84.3
		failCount84 OBJECT-TYPE
			SYNTAX OCTET STRING
			MAX-ACCESS read-write
			STATUS current
			DESCRIPTION
				"Description."
			::= { rub 3 }

		
		-- 1.3.6.1.4.1.19338.19.2.1.84.4
		refusedCount84 OBJECT-TYPE
			SYNTAX OCTET STRING
			MAX-ACCESS read-write
			STATUS current
			DESCRIPTION
				"Description."
			::= { rub 4 }

		
		-- 1.3.6.1.4.1.19338.19.2.1.85
		simACT OBJECT-IDENTITY
			STATUS current
			DESCRIPTION 
				"Description."
			::= { network1 85 }

		
		-- 1.3.6.1.4.1.19338.19.2.1.85.1
		totalINCount85 OBJECT-TYPE
			SYNTAX OCTET STRING
			MAX-ACCESS read-write
			STATUS current
			DESCRIPTION
				"Description."
			::= { simACT 1 }

		
		-- 1.3.6.1.4.1.19338.19.2.1.85.2
		successCount85 OBJECT-TYPE
			SYNTAX OCTET STRING
			MAX-ACCESS read-write
			STATUS current
			DESCRIPTION
				"Description."
			::= { simACT 2 }

		
		-- 1.3.6.1.4.1.19338.19.2.1.85.3
		failCount85 OBJECT-TYPE
			SYNTAX OCTET STRING
			MAX-ACCESS read-write
			STATUS current
			DESCRIPTION
				"Description."
			::= { simACT 3 }

		
		-- 1.3.6.1.4.1.19338.19.2.1.85.4
		refusedCount85 OBJECT-TYPE
			SYNTAX OCTET STRING
			MAX-ACCESS read-write
			STATUS current
			DESCRIPTION
				"Description."
			::= { simACT 4 }

		
		-- 1.3.6.1.4.1.19338.19.2.1.86
		sos OBJECT-IDENTITY
			STATUS current
			DESCRIPTION 
				"Description."
			::= { network1 86 }

		
		-- 1.3.6.1.4.1.19338.19.2.1.86.1
		totalINCount86 OBJECT-TYPE
			SYNTAX OCTET STRING
			MAX-ACCESS read-write
			STATUS current
			DESCRIPTION
				"Description."
			::= { sos 1 }

		
		-- 1.3.6.1.4.1.19338.19.2.1.86.2
		successCount86 OBJECT-TYPE
			SYNTAX OCTET STRING
			MAX-ACCESS read-write
			STATUS current
			DESCRIPTION
				"Description."
			::= { sos 2 }

		
		-- 1.3.6.1.4.1.19338.19.2.1.86.3
		failCount86 OBJECT-TYPE
			SYNTAX OCTET STRING
			MAX-ACCESS read-write
			STATUS current
			DESCRIPTION
				"Description."
			::= { sos 3 }

		
		-- 1.3.6.1.4.1.19338.19.2.1.86.4
		refusedCount86 OBJECT-TYPE
			SYNTAX OCTET STRING
			MAX-ACCESS read-write
			STATUS current
			DESCRIPTION
				"Description."
			::= { sos 4 }

		
		-- 1.3.6.1.4.1.19338.19.2.1.87
		sprc OBJECT-IDENTITY
			STATUS current
			DESCRIPTION 
				"Description."
			::= { network1 87 }

		
		-- 1.3.6.1.4.1.19338.19.2.1.87.1
		totalINCount87 OBJECT-TYPE
			SYNTAX OCTET STRING
			MAX-ACCESS read-write
			STATUS current
			DESCRIPTION
				"Description."
			::= { sprc 1 }

		
		-- 1.3.6.1.4.1.19338.19.2.1.87.2
		successCount87 OBJECT-TYPE
			SYNTAX OCTET STRING
			MAX-ACCESS read-write
			STATUS current
			DESCRIPTION
				"Description."
			::= { sprc 2 }

		
		-- 1.3.6.1.4.1.19338.19.2.1.87.3
		failCount87 OBJECT-TYPE
			SYNTAX OCTET STRING
			MAX-ACCESS read-write
			STATUS current
			DESCRIPTION
				"Description."
			::= { sprc 3 }

		
		-- 1.3.6.1.4.1.19338.19.2.1.87.4
		refusedCount87 OBJECT-TYPE
			SYNTAX OCTET STRING
			MAX-ACCESS read-write
			STATUS current
			DESCRIPTION
				"Description."
			::= { sprc 4 }

		
		-- 1.3.6.1.4.1.19338.19.2.1.88
		sub OBJECT-IDENTITY
			STATUS current
			DESCRIPTION 
				"Description."
			::= { network1 88 }

		
		-- 1.3.6.1.4.1.19338.19.2.1.88.1
		totalINCount88 OBJECT-TYPE
			SYNTAX OCTET STRING
			MAX-ACCESS read-write
			STATUS current
			DESCRIPTION
				"Description."
			::= { sub 1 }

		
		-- 1.3.6.1.4.1.19338.19.2.1.88.2
		successCount88 OBJECT-TYPE
			SYNTAX OCTET STRING
			MAX-ACCESS read-write
			STATUS current
			DESCRIPTION
				"Description."
			::= { sub 2 }

		
		-- 1.3.6.1.4.1.19338.19.2.1.88.3
		failCount88 OBJECT-TYPE
			SYNTAX OCTET STRING
			MAX-ACCESS read-write
			STATUS current
			DESCRIPTION
				"Description."
			::= { sub 3 }

		
		-- 1.3.6.1.4.1.19338.19.2.1.88.4
		refusedCount88 OBJECT-TYPE
			SYNTAX OCTET STRING
			MAX-ACCESS read-write
			STATUS current
			DESCRIPTION
				"Description."
			::= { sub 4 }

		
		-- 1.3.6.1.4.1.19338.19.2.1.89
		susP2PSER OBJECT-IDENTITY
			STATUS current
			DESCRIPTION 
				"Description."
			::= { network1 89 }

		
		-- 1.3.6.1.4.1.19338.19.2.1.89.1
		totalINCount89 OBJECT-TYPE
			SYNTAX OCTET STRING
			MAX-ACCESS read-write
			STATUS current
			DESCRIPTION
				"Description."
			::= { susP2PSER 1 }

		
		-- 1.3.6.1.4.1.19338.19.2.1.89.2
		successCount89 OBJECT-TYPE
			SYNTAX OCTET STRING
			MAX-ACCESS read-write
			STATUS current
			DESCRIPTION
				"Description."
			::= { susP2PSER 2 }

		
		-- 1.3.6.1.4.1.19338.19.2.1.89.3
		failCount89 OBJECT-TYPE
			SYNTAX OCTET STRING
			MAX-ACCESS read-write
			STATUS current
			DESCRIPTION
				"Description."
			::= { susP2PSER 3 }

		
		-- 1.3.6.1.4.1.19338.19.2.1.89.4
		refusedCount89 OBJECT-TYPE
			SYNTAX OCTET STRING
			MAX-ACCESS read-write
			STATUS current
			DESCRIPTION
				"Description."
			::= { susP2PSER 4 }

		
		-- 1.3.6.1.4.1.19338.19.2.1.90
		susRESUSR OBJECT-IDENTITY
			STATUS current
			DESCRIPTION 
				"Description."
			::= { network1 90 }

		
		-- 1.3.6.1.4.1.19338.19.2.1.90.1
		totalINCount90 OBJECT-TYPE
			SYNTAX OCTET STRING
			MAX-ACCESS read-write
			STATUS current
			DESCRIPTION
				"Description."
			::= { susRESUSR 1 }

		
		-- 1.3.6.1.4.1.19338.19.2.1.90.2
		successCount90 OBJECT-TYPE
			SYNTAX OCTET STRING
			MAX-ACCESS read-write
			STATUS current
			DESCRIPTION
				"Description."
			::= { susRESUSR 2 }

		
		-- 1.3.6.1.4.1.19338.19.2.1.90.3
		failCount90 OBJECT-TYPE
			SYNTAX OCTET STRING
			MAX-ACCESS read-write
			STATUS current
			DESCRIPTION
				"Description."
			::= { susRESUSR 3 }

		
		-- 1.3.6.1.4.1.19338.19.2.1.90.4
		refusedCount90 OBJECT-TYPE
			SYNTAX OCTET STRING
			MAX-ACCESS read-write
			STATUS current
			DESCRIPTION
				"Description."
			::= { susRESUSR 4 }

		
		-- 1.3.6.1.4.1.19338.19.2.1.91
		trf OBJECT-IDENTITY
			STATUS current
			DESCRIPTION 
				"Description."
			::= { network1 91 }

		
		-- 1.3.6.1.4.1.19338.19.2.1.91.1
		totalINCount91 OBJECT-TYPE
			SYNTAX OCTET STRING
			MAX-ACCESS read-write
			STATUS current
			DESCRIPTION
				"Description."
			::= { trf 1 }

		
		-- 1.3.6.1.4.1.19338.19.2.1.91.2
		successCount91 OBJECT-TYPE
			SYNTAX OCTET STRING
			MAX-ACCESS read-write
			STATUS current
			DESCRIPTION
				"Description."
			::= { trf 2 }

		
		-- 1.3.6.1.4.1.19338.19.2.1.91.3
		failCount91 OBJECT-TYPE
			SYNTAX OCTET STRING
			MAX-ACCESS read-write
			STATUS current
			DESCRIPTION
				"Description."
			::= { trf 3 }

		
		-- 1.3.6.1.4.1.19338.19.2.1.91.4
		refusedCount91 OBJECT-TYPE
			SYNTAX OCTET STRING
			MAX-ACCESS read-write
			STATUS current
			DESCRIPTION
				"Description."
			::= { trf 4 }

		
		-- 1.3.6.1.4.1.19338.19.2.1.92
		trfRULETYP OBJECT-IDENTITY
			STATUS current
			DESCRIPTION 
				"Description."
			::= { network1 92 }

		
		-- 1.3.6.1.4.1.19338.19.2.1.92.1
		totalINCount92 OBJECT-TYPE
			SYNTAX OCTET STRING
			MAX-ACCESS read-write
			STATUS current
			DESCRIPTION
				"Description."
			::= { trfRULETYP 1 }

		
		-- 1.3.6.1.4.1.19338.19.2.1.92.2
		successCount92 OBJECT-TYPE
			SYNTAX OCTET STRING
			MAX-ACCESS read-write
			STATUS current
			DESCRIPTION
				"Description."
			::= { trfRULETYP 2 }

		
		-- 1.3.6.1.4.1.19338.19.2.1.92.3
		failCount92 OBJECT-TYPE
			SYNTAX OCTET STRING
			MAX-ACCESS read-write
			STATUS current
			DESCRIPTION
				"Description."
			::= { trfRULETYP 3 }

		
		-- 1.3.6.1.4.1.19338.19.2.1.92.4
		refusedCount92 OBJECT-TYPE
			SYNTAX OCTET STRING
			MAX-ACCESS read-write
			STATUS current
			DESCRIPTION
				"Description."
			::= { trfRULETYP 4 }

		
		-- 1.3.6.1.4.1.19338.19.2.1.93
		ubp OBJECT-IDENTITY
			STATUS current
			DESCRIPTION 
				"Description."
			::= { network1 93 }

		
		-- 1.3.6.1.4.1.19338.19.2.1.93.1
		totalINCount93 OBJECT-TYPE
			SYNTAX OCTET STRING
			MAX-ACCESS read-write
			STATUS current
			DESCRIPTION
				"Description."
			::= { ubp 1 }

		
		-- 1.3.6.1.4.1.19338.19.2.1.93.2
		successCount93 OBJECT-TYPE
			SYNTAX OCTET STRING
			MAX-ACCESS read-write
			STATUS current
			DESCRIPTION
				"Description."
			::= { ubp 2 }

		
		-- 1.3.6.1.4.1.19338.19.2.1.93.3
		failCount93 OBJECT-TYPE
			SYNTAX OCTET STRING
			MAX-ACCESS read-write
			STATUS current
			DESCRIPTION
				"Description."
			::= { ubp 3 }

		
		-- 1.3.6.1.4.1.19338.19.2.1.93.4
		refusedCount93 OBJECT-TYPE
			SYNTAX OCTET STRING
			MAX-ACCESS read-write
			STATUS current
			DESCRIPTION
				"Description."
			::= { ubp 4 }

		
		-- 1.3.6.1.4.1.19338.19.2.1.94
		unBARUSER OBJECT-IDENTITY
			STATUS current
			DESCRIPTION 
				"Description."
			::= { network1 94 }

		
		-- 1.3.6.1.4.1.19338.19.2.1.94.1
		totalINCount94 OBJECT-TYPE
			SYNTAX OCTET STRING
			MAX-ACCESS read-write
			STATUS current
			DESCRIPTION
				"Description."
			::= { unBARUSER 1 }

		
		-- 1.3.6.1.4.1.19338.19.2.1.94.2
		successCount94 OBJECT-TYPE
			SYNTAX OCTET STRING
			MAX-ACCESS read-write
			STATUS current
			DESCRIPTION
				"Description."
			::= { unBARUSER 2 }

		
		-- 1.3.6.1.4.1.19338.19.2.1.94.3
		failCount94 OBJECT-TYPE
			SYNTAX OCTET STRING
			MAX-ACCESS read-write
			STATUS current
			DESCRIPTION
				"Description."
			::= { unBARUSER 3 }

		
		-- 1.3.6.1.4.1.19338.19.2.1.94.4
		refusedCount94 OBJECT-TYPE
			SYNTAX OCTET STRING
			MAX-ACCESS read-write
			STATUS current
			DESCRIPTION
				"Description."
			::= { unBARUSER 4 }

		
		-- 1.3.6.1.4.1.19338.19.2.1.95
		usrAUTH OBJECT-IDENTITY
			STATUS current
			DESCRIPTION 
				"Description."
			::= { network1 95 }

		
		-- 1.3.6.1.4.1.19338.19.2.1.95.1
		totalINCount95 OBJECT-TYPE
			SYNTAX OCTET STRING
			MAX-ACCESS read-write
			STATUS current
			DESCRIPTION
				"Description."
			::= { usrAUTH 1 }

		
		-- 1.3.6.1.4.1.19338.19.2.1.95.2
		successCount95 OBJECT-TYPE
			SYNTAX OCTET STRING
			MAX-ACCESS read-write
			STATUS current
			DESCRIPTION
				"Description."
			::= { usrAUTH 2 }

		
		-- 1.3.6.1.4.1.19338.19.2.1.95.3
		failCount95 OBJECT-TYPE
			SYNTAX OCTET STRING
			MAX-ACCESS read-write
			STATUS current
			DESCRIPTION
				"Description."
			::= { usrAUTH 3 }

		
		-- 1.3.6.1.4.1.19338.19.2.1.95.4
		refusedCount95 OBJECT-TYPE
			SYNTAX OCTET STRING
			MAX-ACCESS read-write
			STATUS current
			DESCRIPTION
				"Description."
			::= { usrAUTH 4 }

		
		-- 1.3.6.1.4.1.19338.19.2.1.96
		usrRG OBJECT-IDENTITY
			STATUS current
			DESCRIPTION 
				"Description."
			::= { network1 96 }

		
		-- 1.3.6.1.4.1.19338.19.2.1.96.1
		totalINCount96 OBJECT-TYPE
			SYNTAX OCTET STRING
			MAX-ACCESS read-write
			STATUS current
			DESCRIPTION
				"Description."
			::= { usrRG 1 }

		
		-- 1.3.6.1.4.1.19338.19.2.1.96.2
		successCount96 OBJECT-TYPE
			SYNTAX OCTET STRING
			MAX-ACCESS read-write
			STATUS current
			DESCRIPTION
				"Description."
			::= { usrRG 2 }

		
		-- 1.3.6.1.4.1.19338.19.2.1.96.3
		failCount96 OBJECT-TYPE
			SYNTAX OCTET STRING
			MAX-ACCESS read-write
			STATUS current
			DESCRIPTION
				"Description."
			::= { usrRG 3 }

		
		-- 1.3.6.1.4.1.19338.19.2.1.96.4
		refusedCount96 OBJECT-TYPE
			SYNTAX OCTET STRING
			MAX-ACCESS read-write
			STATUS current
			DESCRIPTION
				"Description."
			::= { usrRG 4 }

		
		-- 1.3.6.1.4.1.19338.19.2.1.97
		vas OBJECT-IDENTITY
			STATUS current
			DESCRIPTION 
				"Description."
			::= { network1 97 }

		
		-- 1.3.6.1.4.1.19338.19.2.1.97.1
		totalINCount97 OBJECT-TYPE
			SYNTAX OCTET STRING
			MAX-ACCESS read-write
			STATUS current
			DESCRIPTION
				"Description."
			::= { vas 1 }

		
		-- 1.3.6.1.4.1.19338.19.2.1.97.2
		successCount97 OBJECT-TYPE
			SYNTAX OCTET STRING
			MAX-ACCESS read-write
			STATUS current
			DESCRIPTION
				"Description."
			::= { vas 2 }

		
		-- 1.3.6.1.4.1.19338.19.2.1.97.3
		failCount97 OBJECT-TYPE
			SYNTAX OCTET STRING
			MAX-ACCESS read-write
			STATUS current
			DESCRIPTION
				"Description."
			::= { vas 3 }

		
		-- 1.3.6.1.4.1.19338.19.2.1.97.4
		refusedCount97 OBJECT-TYPE
			SYNTAX OCTET STRING
			MAX-ACCESS read-write
			STATUS current
			DESCRIPTION
				"Description."
			::= { vas 4 }

		
		-- 1.3.6.1.4.1.19338.19.2.1.98
		viewBARRED OBJECT-IDENTITY
			STATUS current
			DESCRIPTION 
				"Description."
			::= { network1 98 }

		
		-- 1.3.6.1.4.1.19338.19.2.1.98.1
		totalINCount98 OBJECT-TYPE
			SYNTAX OCTET STRING
			MAX-ACCESS read-write
			STATUS current
			DESCRIPTION
				"Description."
			::= { viewBARRED 1 }

		
		-- 1.3.6.1.4.1.19338.19.2.1.98.2
		successCount98 OBJECT-TYPE
			SYNTAX OCTET STRING
			MAX-ACCESS read-write
			STATUS current
			DESCRIPTION
				"Description."
			::= { viewBARRED 2 }

		
		-- 1.3.6.1.4.1.19338.19.2.1.98.3
		failCount98 OBJECT-TYPE
			SYNTAX OCTET STRING
			MAX-ACCESS read-write
			STATUS current
			DESCRIPTION
				"Description."
			::= { viewBARRED 3 }

		
		-- 1.3.6.1.4.1.19338.19.2.1.98.4
		refusedCount98 OBJECT-TYPE
			SYNTAX OCTET STRING
			MAX-ACCESS read-write
			STATUS current
			DESCRIPTION
				"Description."
			::= { viewBARRED 4 }

		
		-- 1.3.6.1.4.1.19338.19.2.1.99
		viewCUSER OBJECT-IDENTITY
			STATUS current
			DESCRIPTION 
				"Description."
			::= { network1 99 }

		
		-- 1.3.6.1.4.1.19338.19.2.1.99.1
		totalINCount99 OBJECT-TYPE
			SYNTAX OCTET STRING
			MAX-ACCESS read-write
			STATUS current
			DESCRIPTION
				"Description."
			::= { viewCUSER 1 }

		
		-- 1.3.6.1.4.1.19338.19.2.1.99.2
		successCount99 OBJECT-TYPE
			SYNTAX OCTET STRING
			MAX-ACCESS read-write
			STATUS current
			DESCRIPTION
				"Description."
			::= { viewCUSER 2 }

		
		-- 1.3.6.1.4.1.19338.19.2.1.99.3
		failCount99 OBJECT-TYPE
			SYNTAX OCTET STRING
			MAX-ACCESS read-write
			STATUS current
			DESCRIPTION
				"Description."
			::= { viewCUSER 3 }

		
		-- 1.3.6.1.4.1.19338.19.2.1.99.4
		refusedCount99 OBJECT-TYPE
			SYNTAX OCTET STRING
			MAX-ACCESS read-write
			STATUS current
			DESCRIPTION
				"Description."
			::= { viewCUSER 4 }

		
		-- 1.3.6.1.4.1.19338.19.2.1.100
		viewREGSUB OBJECT-IDENTITY
			STATUS current
			DESCRIPTION 
				"Description."
			::= { network1 100 }

		
		-- 1.3.6.1.4.1.19338.19.2.1.100.1
		totalINCount100 OBJECT-TYPE
			SYNTAX OCTET STRING
			MAX-ACCESS read-write
			STATUS current
			DESCRIPTION
				"Description."
			::= { viewREGSUB 1 }

		
		-- 1.3.6.1.4.1.19338.19.2.1.100.2
		successCount100 OBJECT-TYPE
			SYNTAX OCTET STRING
			MAX-ACCESS read-write
			STATUS current
			DESCRIPTION
				"Description."
			::= { viewREGSUB 2 }

		
		-- 1.3.6.1.4.1.19338.19.2.1.100.3
		failCount100 OBJECT-TYPE
			SYNTAX OCTET STRING
			MAX-ACCESS read-write
			STATUS current
			DESCRIPTION
				"Description."
			::= { viewREGSUB 3 }

		
		-- 1.3.6.1.4.1.19338.19.2.1.100.4
		refusedCount100 OBJECT-TYPE
			SYNTAX OCTET STRING
			MAX-ACCESS read-write
			STATUS current
			DESCRIPTION
				"Description."
			::= { viewREGSUB 4 }

		
		-- 1.3.6.1.4.1.19338.19.2.1.101
		viewTRF OBJECT-IDENTITY
			STATUS current
			DESCRIPTION 
				"Description."
			::= { network1 101 }

		
		-- 1.3.6.1.4.1.19338.19.2.1.101.1
		totalINCount101 OBJECT-TYPE
			SYNTAX OCTET STRING
			MAX-ACCESS read-write
			STATUS current
			DESCRIPTION
				"Description."
			::= { viewTRF 1 }

		
		-- 1.3.6.1.4.1.19338.19.2.1.101.2
		successCount101 OBJECT-TYPE
			SYNTAX OCTET STRING
			MAX-ACCESS read-write
			STATUS current
			DESCRIPTION
				"Description."
			::= { viewTRF 2 }

		
		-- 1.3.6.1.4.1.19338.19.2.1.101.3
		failCount101 OBJECT-TYPE
			SYNTAX OCTET STRING
			MAX-ACCESS read-write
			STATUS current
			DESCRIPTION
				"Description."
			::= { viewTRF 3 }

		
		-- 1.3.6.1.4.1.19338.19.2.1.101.4
		refusedCount101 OBJECT-TYPE
			SYNTAX OCTET STRING
			MAX-ACCESS read-write
			STATUS current
			DESCRIPTION
				"Description."
			::= { viewTRF 4 }

		
		-- 1.3.6.1.4.1.19338.19.2.1.102
		wd OBJECT-IDENTITY
			STATUS current
			DESCRIPTION 
				"Description."
			::= { network1 102 }

		
		-- 1.3.6.1.4.1.19338.19.2.1.102.1
		totalINCount102 OBJECT-TYPE
			SYNTAX OCTET STRING
			MAX-ACCESS read-write
			STATUS current
			DESCRIPTION
				"Description."
			::= { wd 1 }

		
		-- 1.3.6.1.4.1.19338.19.2.1.102.2
		successCount102 OBJECT-TYPE
			SYNTAX OCTET STRING
			MAX-ACCESS read-write
			STATUS current
			DESCRIPTION
				"Description."
			::= { wd 2 }

		
		-- 1.3.6.1.4.1.19338.19.2.1.102.3
		failCount102 OBJECT-TYPE
			SYNTAX OCTET STRING
			MAX-ACCESS read-write
			STATUS current
			DESCRIPTION
				"Description."
			::= { wd 3 }

		
		-- 1.3.6.1.4.1.19338.19.2.1.102.4
		refusedCount102 OBJECT-TYPE
			SYNTAX OCTET STRING
			MAX-ACCESS read-write
			STATUS current
			DESCRIPTION
				"Description."
			::= { wd 4 }

		
		-- 1.3.6.1.4.1.19338.19.2.1.103
		whtlstENQ OBJECT-IDENTITY
			STATUS current
			DESCRIPTION 
				"Description."
			::= { network1 103 }

		
		-- 1.3.6.1.4.1.19338.19.2.1.103.1
		totalINCount103 OBJECT-TYPE
			SYNTAX OCTET STRING
			MAX-ACCESS read-write
			STATUS current
			DESCRIPTION
				"Description."
			::= { whtlstENQ 1 }

		
		-- 1.3.6.1.4.1.19338.19.2.1.103.2
		successCount103 OBJECT-TYPE
			SYNTAX OCTET STRING
			MAX-ACCESS read-write
			STATUS current
			DESCRIPTION
				"Description."
			::= { whtlstENQ 2 }

		
		-- 1.3.6.1.4.1.19338.19.2.1.103.3
		failCount103 OBJECT-TYPE
			SYNTAX OCTET STRING
			MAX-ACCESS read-write
			STATUS current
			DESCRIPTION
				"Description."
			::= { whtlstENQ 3 }

		
		-- 1.3.6.1.4.1.19338.19.2.1.103.4
		refusedCount103 OBJECT-TYPE
			SYNTAX OCTET STRING
			MAX-ACCESS read-write
			STATUS current
			DESCRIPTION
				"Description."
			::= { whtlstENQ 4 }

		
		-- 1.3.6.1.4.1.19338.19.2.2
		alarms OBJECT-IDENTITY
			STATUS current
			DESCRIPTION 
				"Description."
			::= { instance1 2 }

		
		-- 1.3.6.1.4.1.19338.19.2.2.1
		dbConnectionIssue NOTIFICATION-TYPE
			OBJECTS { exitStatus, alarmString, misc, alarmType, alarmStatus
				 }
			STATUS current
			DESCRIPTION 
				"Description."
			::= { alarms 1 }

		
		-- 1.3.6.1.4.1.19338.19.2.2.2
		systemError NOTIFICATION-TYPE
			OBJECTS { exitStatus, alarmString, misc, alarmType, alarmStatus
				 }
			STATUS current
			DESCRIPTION 
				"Description."
			::= { alarms 2 }

		
		-- 1.3.6.1.4.1.19338.19.2.2.3
		systemInfo NOTIFICATION-TYPE
			OBJECTS { exitStatus, alarmString, misc, alarmType, alarmStatus
				 }
			STATUS current
			DESCRIPTION 
				"Description."
			::= { alarms 3 }

		
		-- 1.3.6.1.4.1.19338.19.2.2.4
		interfaceinvalidResponse NOTIFICATION-TYPE
			OBJECTS { exitStatus, alarmString, misc, alarmType, alarmStatus
				 }
			STATUS current
			DESCRIPTION 
				"Description."
			::= { alarms 4 }

		
		-- 1.3.6.1.4.1.19338.19.2.2.5
		retryAttemptFailed NOTIFICATION-TYPE
			OBJECTS { exitStatus, alarmString, misc, alarmType, alarmStatus
				 }
			STATUS current
			DESCRIPTION 
				"Description."
			::= { alarms 5 }

		
		-- 1.3.6.1.4.1.19338.19.2.2.6
		interfaceRequestException NOTIFICATION-TYPE
			OBJECTS { exitStatus, alarmString, misc, alarmType, alarmStatus
				 }
			STATUS current
			DESCRIPTION 
				"Description."
			::= { alarms 6 }

		
		-- 1.3.6.1.4.1.19338.19.2.2.7
		interfaceResponseException NOTIFICATION-TYPE
			OBJECTS { exitStatus, alarmString, misc, alarmType, alarmStatus
				 }
			STATUS current
			DESCRIPTION 
				"Description."
			::= { alarms 7 }

		
		-- 1.3.6.1.4.1.19338.19.2.2.8
		adminOpt NOTIFICATION-TYPE
			OBJECTS { exitStatus, alarmString, misc, alarmType, alarmStatus
				 }
			STATUS current
			DESCRIPTION 
				"Description."
			::= { alarms 8 }

		
		-- 1.3.6.1.4.1.19338.19.2.2.9
		networkSuspended NOTIFICATION-TYPE
			OBJECTS { exitStatus, alarmString, misc, alarmType, alarmStatus
				 }
			STATUS current
			DESCRIPTION 
				"Description."
			::= { alarms 9 }

		
		-- 1.3.6.1.4.1.19338.19.2.2.10
		productSuspended NOTIFICATION-TYPE
			OBJECTS { exitStatus, alarmString, misc, alarmType, alarmStatus
				 }
			STATUS current
			DESCRIPTION 
				"Description."
			::= { alarms 10 }

		
		-- 1.3.6.1.4.1.19338.19.2.2.11
		cardGroupSuspended NOTIFICATION-TYPE
			OBJECTS { exitStatus, alarmString, misc, alarmType, alarmStatus
				 }
			STATUS current
			DESCRIPTION 
				"Description."
			::= { alarms 11 }

		
		-- 1.3.6.1.4.1.19338.19.2.2.12
		cardGroupSlabNotFound NOTIFICATION-TYPE
			OBJECTS { exitStatus, alarmString, misc, alarmType, alarmStatus
				 }
			STATUS current
			DESCRIPTION 
				"Description."
			::= { alarms 12 }

		
		-- 1.3.6.1.4.1.19338.19.2.2.13
		cardGroupException NOTIFICATION-TYPE
			OBJECTS { exitStatus, alarmString, misc, alarmType, alarmStatus
				 }
			STATUS current
			DESCRIPTION 
				"Description."
			::= { alarms 13 }

		
		-- 1.3.6.1.4.1.19338.19.2.2.14
		cardgroupNotFound NOTIFICATION-TYPE
			OBJECTS { exitStatus, alarmString, misc, alarmType, alarmStatus
				 }
			STATUS current
			DESCRIPTION 
				"Description."
			::= { alarms 14 }

		
		-- 1.3.6.1.4.1.19338.19.2.2.15
		requestFailDuetoBlockTime NOTIFICATION-TYPE
			OBJECTS { exitStatus, alarmString, misc, alarmType, alarmStatus
				 }
			STATUS current
			DESCRIPTION 
				"Description."
			::= { alarms 15 }

		
		-- 1.3.6.1.4.1.19338.19.2.2.16
		reqFailDuetoDayMaxLimit NOTIFICATION-TYPE
			OBJECTS { exitStatus, alarmString, misc, alarmType, alarmStatus
				 }
			STATUS current
			DESCRIPTION 
				"Description."
			::= { alarms 16 }

		
		-- 1.3.6.1.4.1.19338.19.2.2.17
		reqFailDueToDayMaxAMTLimit NOTIFICATION-TYPE
			OBJECTS { exitStatus, alarmString, misc, alarmType, alarmStatus
				 }
			STATUS current
			DESCRIPTION 
				"Description."
			::= { alarms 17 }

		
		-- 1.3.6.1.4.1.19338.19.2.2.18
		reqFailDueToWeekMaxLimit NOTIFICATION-TYPE
			OBJECTS { exitStatus, alarmString, misc, alarmType, alarmStatus
				 }
			STATUS current
			DESCRIPTION 
				"Description."
			::= { alarms 18 }

		
		-- 1.3.6.1.4.1.19338.19.2.2.19
		reqFailDuetoWeekMaxAmtLimit NOTIFICATION-TYPE
			OBJECTS { exitStatus, alarmString, misc, alarmType, alarmStatus
				 }
			STATUS current
			DESCRIPTION 
				"Description."
			::= { alarms 19 }

		
		-- 1.3.6.1.4.1.19338.19.2.2.20
		reqFailDueToMonthMaxLimit NOTIFICATION-TYPE
			OBJECTS { exitStatus, alarmString, misc, alarmType, alarmStatus
				 }
			STATUS current
			DESCRIPTION 
				"Description."
			::= { alarms 20 }

		
		-- 1.3.6.1.4.1.19338.19.2.2.21
		reqFailDueToMonthMaxAmtLimit NOTIFICATION-TYPE
			OBJECTS { exitStatus, alarmString, misc, alarmType, alarmStatus
				 }
			STATUS current
			DESCRIPTION 
				"Description."
			::= { alarms 21 }

		
		-- 1.3.6.1.4.1.19338.19.2.2.22
		reqAmtNotInRange NOTIFICATION-TYPE
			OBJECTS { exitStatus, alarmString, misc, alarmType, alarmStatus
				 }
			STATUS current
			DESCRIPTION 
				"Description."
			::= { alarms 22 }

		
		-- 1.3.6.1.4.1.19338.19.2.2.23
		invalidPin NOTIFICATION-TYPE
			OBJECTS { exitStatus, alarmString, misc, alarmType, alarmStatus
				 }
			STATUS current
			DESCRIPTION 
				"Description."
			::= { alarms 23 }

		
		-- 1.3.6.1.4.1.19338.19.2.2.24
		pinBlocked NOTIFICATION-TYPE
			OBJECTS { exitStatus, alarmString, misc, alarmType, alarmStatus
				 }
			STATUS current
			DESCRIPTION 
				"Description."
			::= { alarms 24 }

		
		-- 1.3.6.1.4.1.19338.19.2.2.25
		maxLocationLoadReached NOTIFICATION-TYPE
			OBJECTS { exitStatus, alarmString, misc, alarmType, alarmStatus
				 }
			STATUS current
			DESCRIPTION 
				"Description."
			::= { alarms 25 }

		
		-- 1.3.6.1.4.1.19338.19.2.2.26
		locationRechargeSystemOverLoaded NOTIFICATION-TYPE
			OBJECTS { exitStatus, alarmString, misc, alarmType, alarmStatus
				 }
			STATUS current
			DESCRIPTION 
				"Description."
			::= { alarms 26 }

		
		-- 1.3.6.1.4.1.19338.19.2.3
		network2 OBJECT-IDENTITY
			STATUS current
			DESCRIPTION 
				"Description."
			::= { instance1 3 }

		
		-- 1.3.6.1.4.1.19338.19.2.3.1
		all1 OBJECT-IDENTITY
			STATUS current
			DESCRIPTION 
				"Description."
			::= { network2 1 }

		
		-- 1.3.6.1.4.1.19338.19.2.3.1.1
		totalINCount104 OBJECT-TYPE
			SYNTAX OCTET STRING
			MAX-ACCESS read-write
			STATUS current
			DESCRIPTION
				"Description."
			::= { all1 1 }

		
		-- 1.3.6.1.4.1.19338.19.2.3.1.2
		successCount104 OBJECT-TYPE
			SYNTAX OCTET STRING
			MAX-ACCESS read-write
			STATUS current
			DESCRIPTION
				"Description."
			::= { all1 2 }

		
		-- 1.3.6.1.4.1.19338.19.2.3.1.3
		failCount104 OBJECT-TYPE
			SYNTAX OCTET STRING
			MAX-ACCESS read-write
			STATUS current
			DESCRIPTION
				"Description."
			::= { all1 3 }

		
		-- 1.3.6.1.4.1.19338.19.2.3.1.4
		refusedCount104 OBJECT-TYPE
			SYNTAX OCTET STRING
			MAX-ACCESS read-write
			STATUS current
			DESCRIPTION
				"Description."
			::= { all1 4 }

		
		-- 1.3.6.1.4.1.19338.19.2.3.2
		accinfo1 OBJECT-IDENTITY
			STATUS current
			DESCRIPTION 
				"Description."
			::= { network2 2 }

		
		-- 1.3.6.1.4.1.19338.19.2.3.2.1
		totalINCount105 OBJECT-TYPE
			SYNTAX OCTET STRING
			MAX-ACCESS read-write
			STATUS current
			DESCRIPTION
				"Description."
			::= { accinfo1 1 }

		
		-- 1.3.6.1.4.1.19338.19.2.3.2.2
		successCount105 OBJECT-TYPE
			SYNTAX OCTET STRING
			MAX-ACCESS read-write
			STATUS current
			DESCRIPTION
				"Description."
			::= { accinfo1 2 }

		
		-- 1.3.6.1.4.1.19338.19.2.3.2.3
		failCount105 OBJECT-TYPE
			SYNTAX OCTET STRING
			MAX-ACCESS read-write
			STATUS current
			DESCRIPTION
				"Description."
			::= { accinfo1 3 }

		
		-- 1.3.6.1.4.1.19338.19.2.3.2.4
		refusedCount105 OBJECT-TYPE
			SYNTAX OCTET STRING
			MAX-ACCESS read-write
			STATUS current
			DESCRIPTION
				"Description."
			::= { accinfo1 4 }

		
		-- 1.3.6.1.4.1.19338.19.2.3.3
		adm1 OBJECT-IDENTITY
			STATUS current
			DESCRIPTION 
				"Description."
			::= { network2 3 }

		
		-- 1.3.6.1.4.1.19338.19.2.3.3.1
		totalINCount106 OBJECT-TYPE
			SYNTAX OCTET STRING
			MAX-ACCESS read-write
			STATUS current
			DESCRIPTION
				"Description."
			::= { adm1 1 }

		
		-- 1.3.6.1.4.1.19338.19.2.3.3.2
		successCount106 OBJECT-TYPE
			SYNTAX OCTET STRING
			MAX-ACCESS read-write
			STATUS current
			DESCRIPTION
				"Description."
			::= { adm1 2 }

		
		-- 1.3.6.1.4.1.19338.19.2.3.3.3
		ffailCount106 OBJECT-TYPE
			SYNTAX OCTET STRING
			MAX-ACCESS read-write
			STATUS current
			DESCRIPTION
				"Description."
			::= { adm1 3 }

		
		-- 1.3.6.1.4.1.19338.19.2.3.3.4
		refusedCount106 OBJECT-TYPE
			SYNTAX OCTET STRING
			MAX-ACCESS read-write
			STATUS current
			DESCRIPTION
				"Description."
			::= { adm1 4 }

		
		-- 1.3.6.1.4.1.19338.19.2.3.4
		bar1 OBJECT-IDENTITY
			STATUS current
			DESCRIPTION 
				"Description."
			::= { network2 4 }

		
		-- 1.3.6.1.4.1.19338.19.2.3.4.1
		totalINCount107 OBJECT-TYPE
			SYNTAX OCTET STRING
			MAX-ACCESS read-write
			STATUS current
			DESCRIPTION
				"Description."
			::= { bar1 1 }

		
		-- 1.3.6.1.4.1.19338.19.2.3.4.2
		successCount107 OBJECT-TYPE
			SYNTAX OCTET STRING
			MAX-ACCESS read-write
			STATUS current
			DESCRIPTION
				"Description."
			::= { bar1 2 }

		
		-- 1.3.6.1.4.1.19338.19.2.3.4.3
		failCount107 OBJECT-TYPE
			SYNTAX OCTET STRING
			MAX-ACCESS read-write
			STATUS current
			DESCRIPTION
				"Description."
			::= { bar1 3 }

		
		-- 1.3.6.1.4.1.19338.19.2.3.4.4
		refusedCount107 OBJECT-TYPE
			SYNTAX OCTET STRING
			MAX-ACCESS read-write
			STATUS current
			DESCRIPTION
				"Description."
			::= { bar1 4 }

		
		-- 1.3.6.1.4.1.19338.19.2.3.5
		barUser1 OBJECT-IDENTITY
			STATUS current
			DESCRIPTION 
				"Description."
			::= { network2 5 }

		
		-- 1.3.6.1.4.1.19338.19.2.3.5.1
		totalINCount108 OBJECT-TYPE
			SYNTAX OCTET STRING
			MAX-ACCESS read-write
			STATUS current
			DESCRIPTION
				"Description."
			::= { barUser1 1 }

		
		-- 1.3.6.1.4.1.19338.19.2.3.5.2
		successCount108 OBJECT-TYPE
			SYNTAX OCTET STRING
			MAX-ACCESS read-write
			STATUS current
			DESCRIPTION
				"Description."
			::= { barUser1 2 }

		
		-- 1.3.6.1.4.1.19338.19.2.3.5.3
		failCount108 OBJECT-TYPE
			SYNTAX OCTET STRING
			MAX-ACCESS read-write
			STATUS current
			DESCRIPTION
				"Description."
			::= { barUser1 3 }

		
		-- 1.3.6.1.4.1.19338.19.2.3.5.4
		refusedCount108 OBJECT-TYPE
			SYNTAX OCTET STRING
			MAX-ACCESS read-write
			STATUS current
			DESCRIPTION
				"Description."
			::= { barUser1 4 }

		
		-- 1.3.6.1.4.1.19338.19.2.3.6
		c2cTRFENQ1 OBJECT-IDENTITY
			STATUS current
			DESCRIPTION 
				"Description."
			::= { network2 6 }

		
		-- 1.3.6.1.4.1.19338.19.2.3.6.1
		totalINCount109 OBJECT-TYPE
			SYNTAX OCTET STRING
			MAX-ACCESS read-write
			STATUS current
			DESCRIPTION
				"Description."
			::= { c2cTRFENQ1 1 }

		
		-- 1.3.6.1.4.1.19338.19.2.3.6.2
		successCount109 OBJECT-TYPE
			SYNTAX OCTET STRING
			MAX-ACCESS read-write
			STATUS current
			DESCRIPTION
				"Description."
			::= { c2cTRFENQ1 2 }

		
		-- 1.3.6.1.4.1.19338.19.2.3.6.3
		failCount109 OBJECT-TYPE
			SYNTAX OCTET STRING
			MAX-ACCESS read-write
			STATUS current
			DESCRIPTION
				"Description."
			::= { c2cTRFENQ1 3 }

		
		-- 1.3.6.1.4.1.19338.19.2.3.6.4
		refusedCount109 OBJECT-TYPE
			SYNTAX OCTET STRING
			MAX-ACCESS read-write
			STATUS current
			DESCRIPTION
				"Description."
			::= { c2cTRFENQ1 4 }

		
		-- 1.3.6.1.4.1.19338.19.2.3.7
		c2sBal1 OBJECT-IDENTITY
			STATUS current
			DESCRIPTION 
				"Description."
			::= { network2 7 }

		
		-- 1.3.6.1.4.1.19338.19.2.3.7.1
		totalINCount110 OBJECT-TYPE
			SYNTAX OCTET STRING
			MAX-ACCESS read-write
			STATUS current
			DESCRIPTION
				"Description."
			::= { c2sBal1 1 }

		
		-- 1.3.6.1.4.1.19338.19.2.3.7.2
		successCount110 OBJECT-TYPE
			SYNTAX OCTET STRING
			MAX-ACCESS read-write
			STATUS current
			DESCRIPTION
				"Description."
			::= { c2sBal1 2 }

		
		-- 1.3.6.1.4.1.19338.19.2.3.7.3
		failCount110 OBJECT-TYPE
			SYNTAX OCTET STRING
			MAX-ACCESS read-write
			STATUS current
			DESCRIPTION
				"Description."
			::= { c2sBal1 3 }

		
		-- 1.3.6.1.4.1.19338.19.2.3.7.4
		refusedCount110 OBJECT-TYPE
			SYNTAX OCTET STRING
			MAX-ACCESS read-write
			STATUS current
			DESCRIPTION
				"Description."
			::= { c2sBal1 4 }

		
		-- 1.3.6.1.4.1.19338.19.2.3.8
		c2sCpn1 OBJECT-IDENTITY
			STATUS current
			DESCRIPTION 
				"Description."
			::= { network2 8 }

		
		-- 1.3.6.1.4.1.19338.19.2.3.8.1
		totalINCount111 OBJECT-TYPE
			SYNTAX OCTET STRING
			MAX-ACCESS read-write
			STATUS current
			DESCRIPTION
				"Description."
			::= { c2sCpn1 1 }

		
		-- 1.3.6.1.4.1.19338.19.2.3.8.2
		successCount111 OBJECT-TYPE
			SYNTAX OCTET STRING
			MAX-ACCESS read-write
			STATUS current
			DESCRIPTION
				"Description."
			::= { c2sCpn1 2 }

		
		-- 1.3.6.1.4.1.19338.19.2.3.8.3
		failCount111 OBJECT-TYPE
			SYNTAX OCTET STRING
			MAX-ACCESS read-write
			STATUS current
			DESCRIPTION
				"Description."
			::= { c2sCpn1 3 }

		
		-- 1.3.6.1.4.1.19338.19.2.3.8.4
		refusedCount111 OBJECT-TYPE
			SYNTAX OCTET STRING
			MAX-ACCESS read-write
			STATUS current
			DESCRIPTION
				"Description."
			::= { c2sCpn1 4 }

		
		-- 1.3.6.1.4.1.19338.19.2.3.9
		c2sDAILYTR1 OBJECT-IDENTITY
			STATUS current
			DESCRIPTION 
				"Description."
			::= { network2 9 }

		
		-- 1.3.6.1.4.1.19338.19.2.3.9.1
		totalINCount112 OBJECT-TYPE
			SYNTAX OCTET STRING
			MAX-ACCESS read-write
			STATUS current
			DESCRIPTION
				"Description."
			::= { c2sDAILYTR1 1 }

		
		-- 1.3.6.1.4.1.19338.19.2.3.9.2
		successCount112 OBJECT-TYPE
			SYNTAX OCTET STRING
			MAX-ACCESS read-write
			STATUS current
			DESCRIPTION
				"Description."
			::= { c2sDAILYTR1 2 }

		
		-- 1.3.6.1.4.1.19338.19.2.3.9.3
		failCount112 OBJECT-TYPE
			SYNTAX OCTET STRING
			MAX-ACCESS read-write
			STATUS current
			DESCRIPTION
				"Description."
			::= { c2sDAILYTR1 3 }

		
		-- 1.3.6.1.4.1.19338.19.2.3.9.4
		refusedCount112 OBJECT-TYPE
			SYNTAX OCTET STRING
			MAX-ACCESS read-write
			STATUS current
			DESCRIPTION
				"Description."
			::= { c2sDAILYTR1 4 }

		
		-- 1.3.6.1.4.1.19338.19.2.3.10
		c2sENQ1 OBJECT-IDENTITY
			STATUS current
			DESCRIPTION 
				"Description."
			::= { network2 10 }

		
		-- 1.3.6.1.4.1.19338.19.2.3.10.1
		totalINCount113 OBJECT-TYPE
			SYNTAX OCTET STRING
			MAX-ACCESS read-write
			STATUS current
			DESCRIPTION
				"Description."
			::= { c2sENQ1 1 }

		
		-- 1.3.6.1.4.1.19338.19.2.3.10.2
		successCount113 OBJECT-TYPE
			SYNTAX OCTET STRING
			MAX-ACCESS read-write
			STATUS current
			DESCRIPTION
				"Description."
			::= { c2sENQ1 2 }

		
		-- 1.3.6.1.4.1.19338.19.2.3.10.3
		failCount113 OBJECT-TYPE
			SYNTAX OCTET STRING
			MAX-ACCESS read-write
			STATUS current
			DESCRIPTION
				"Description."
			::= { c2sENQ1 3 }

		
		-- 1.3.6.1.4.1.19338.19.2.3.10.4
		refusedCount113 OBJECT-TYPE
			SYNTAX OCTET STRING
			MAX-ACCESS read-write
			STATUS current
			DESCRIPTION
				"Description."
			::= { c2sENQ1 4 }

		
		-- 1.3.6.1.4.1.19338.19.2.3.11
		c2sLASTTRF1 OBJECT-IDENTITY
			STATUS current
			DESCRIPTION 
				"Description."
			::= { network2 11 }

		
		-- 1.3.6.1.4.1.19338.19.2.3.11.1
		totalINCount114 OBJECT-TYPE
			SYNTAX OCTET STRING
			MAX-ACCESS read-write
			STATUS current
			DESCRIPTION
				"Description."
			::= { c2sLASTTRF1 1 }

		
		-- 1.3.6.1.4.1.19338.19.2.3.11.2
		successCount114 OBJECT-TYPE
			SYNTAX OCTET STRING
			MAX-ACCESS read-write
			STATUS current
			DESCRIPTION
				"Description."
			::= { c2sLASTTRF1 2 }

		
		-- 1.3.6.1.4.1.19338.19.2.3.11.3
		failCount114 OBJECT-TYPE
			SYNTAX OCTET STRING
			MAX-ACCESS read-write
			STATUS current
			DESCRIPTION
				"Description."
			::= { c2sLASTTRF1 3 }

		
		-- 1.3.6.1.4.1.19338.19.2.3.11.4
		refusedCount114 OBJECT-TYPE
			SYNTAX OCTET STRING
			MAX-ACCESS read-write
			STATUS current
			DESCRIPTION
				"Description."
			::= { c2sLASTTRF1 4 }

		
		-- 1.3.6.1.4.1.19338.19.2.3.12
		c2sLASXTRF1 OBJECT-IDENTITY
			STATUS current
			DESCRIPTION 
				"Description."
			::= { network2 12 }

		
		-- 1.3.6.1.4.1.19338.19.2.3.12.1
		totalINCount115 OBJECT-TYPE
			SYNTAX OCTET STRING
			MAX-ACCESS read-write
			STATUS current
			DESCRIPTION
				"Description."
			::= { c2sLASXTRF1 1 }

		
		-- 1.3.6.1.4.1.19338.19.2.3.12.2
		successCount115 OBJECT-TYPE
			SYNTAX OCTET STRING
			MAX-ACCESS read-write
			STATUS current
			DESCRIPTION
				"Description."
			::= { c2sLASXTRF1 2 }

		
		-- 1.3.6.1.4.1.19338.19.2.3.12.3
		failCount115 OBJECT-TYPE
			SYNTAX OCTET STRING
			MAX-ACCESS read-write
			STATUS current
			DESCRIPTION
				"Description."
			::= { c2sLASXTRF1 3 }

		
		-- 1.3.6.1.4.1.19338.19.2.3.12.4
		refusedCount115 OBJECT-TYPE
			SYNTAX OCTET STRING
			MAX-ACCESS read-write
			STATUS current
			DESCRIPTION
				"Description."
			::= { c2sLASXTRF1 4 }

		
		-- 1.3.6.1.4.1.19338.19.2.3.13
		c2sTRFENQ1 OBJECT-IDENTITY
			STATUS current
			DESCRIPTION 
				"Description."
			::= { network2 13 }

		
		-- 1.3.6.1.4.1.19338.19.2.3.13.1
		totalINCount116 OBJECT-TYPE
			SYNTAX OCTET STRING
			MAX-ACCESS read-write
			STATUS current
			DESCRIPTION
				"Description."
			::= { c2sTRFENQ1 1 }

		
		-- 1.3.6.1.4.1.19338.19.2.3.13.2
		successCount116 OBJECT-TYPE
			SYNTAX OCTET STRING
			MAX-ACCESS read-write
			STATUS current
			DESCRIPTION
				"Description."
			::= { c2sTRFENQ1 2 }

		
		-- 1.3.6.1.4.1.19338.19.2.3.13.3
		failCount116 OBJECT-TYPE
			SYNTAX OCTET STRING
			MAX-ACCESS read-write
			STATUS current
			DESCRIPTION
				"Description."
			::= { c2sTRFENQ1 3 }

		
		-- 1.3.6.1.4.1.19338.19.2.3.13.4
		refusedCount116 OBJECT-TYPE
			SYNTAX OCTET STRING
			MAX-ACCESS read-write
			STATUS current
			DESCRIPTION
				"Description."
			::= { c2sTRFENQ1 4 }

		
		-- 1.3.6.1.4.1.19338.19.2.3.14
		c2sUNBLKPN1 OBJECT-IDENTITY
			STATUS current
			DESCRIPTION 
				"Description."
			::= { network2 14 }

		
		-- 1.3.6.1.4.1.19338.19.2.3.14.1
		totalINCount117 OBJECT-TYPE
			SYNTAX OCTET STRING
			MAX-ACCESS read-write
			STATUS current
			DESCRIPTION
				"Description."
			::= { c2sUNBLKPN1 1 }

		
		-- 1.3.6.1.4.1.19338.19.2.3.14.2
		successCount117 OBJECT-TYPE
			SYNTAX OCTET STRING
			MAX-ACCESS read-write
			STATUS current
			DESCRIPTION
				"Description."
			::= { c2sUNBLKPN1 2 }

		
		-- 1.3.6.1.4.1.19338.19.2.3.14.3
		failCount117 OBJECT-TYPE
			SYNTAX OCTET STRING
			MAX-ACCESS read-write
			STATUS current
			DESCRIPTION
				"Description."
			::= { c2sUNBLKPN1 3 }

		
		-- 1.3.6.1.4.1.19338.19.2.3.14.4
		refusedCount117 OBJECT-TYPE
			SYNTAX OCTET STRING
			MAX-ACCESS read-write
			STATUS current
			DESCRIPTION
				"Description."
			::= { c2sUNBLKPN1 4 }

		
		-- 1.3.6.1.4.1.19338.19.2.3.15
		c2sUNBLOCK1 OBJECT-IDENTITY
			STATUS current
			DESCRIPTION 
				"Description."
			::= { network2 15 }

		
		-- 1.3.6.1.4.1.19338.19.2.3.15.1
		totalINCount118 OBJECT-TYPE
			SYNTAX OCTET STRING
			MAX-ACCESS read-write
			STATUS current
			DESCRIPTION
				"Description."
			::= { c2sUNBLOCK1 1 }

		
		-- 1.3.6.1.4.1.19338.19.2.3.15.2
		successCount118 OBJECT-TYPE
			SYNTAX OCTET STRING
			MAX-ACCESS read-write
			STATUS current
			DESCRIPTION
				"Description."
			::= { c2sUNBLOCK1 2 }

		
		-- 1.3.6.1.4.1.19338.19.2.3.15.3
		failCount118 OBJECT-TYPE
			SYNTAX OCTET STRING
			MAX-ACCESS read-write
			STATUS current
			DESCRIPTION
				"Description."
			::= { c2sUNBLOCK1 3 }

		
		-- 1.3.6.1.4.1.19338.19.2.3.15.4
		refusedCount118 OBJECT-TYPE
			SYNTAX OCTET STRING
			MAX-ACCESS read-write
			STATUS current
			DESCRIPTION
				"Description."
			::= { c2sUNBLOCK1 4 }

		
		-- 1.3.6.1.4.1.19338.19.2.3.16
		cARDDL1 OBJECT-IDENTITY
			STATUS current
			DESCRIPTION 
				"Description."
			::= { network2 16 }

		
		-- 1.3.6.1.4.1.19338.19.2.3.16.1
		totalINCount119 OBJECT-TYPE
			SYNTAX OCTET STRING
			MAX-ACCESS read-write
			STATUS current
			DESCRIPTION
				"Description."
			::= { cARDDL1 1 }

		
		-- 1.3.6.1.4.1.19338.19.2.3.16.2
		successCount119 OBJECT-TYPE
			SYNTAX OCTET STRING
			MAX-ACCESS read-write
			STATUS current
			DESCRIPTION
				"Description."
			::= { cARDDL1 2 }

		
		-- 1.3.6.1.4.1.19338.19.2.3.16.3
		failCount119 OBJECT-TYPE
			SYNTAX OCTET STRING
			MAX-ACCESS read-write
			STATUS current
			DESCRIPTION
				"Description."
			::= { cARDDL1 3 }

		
		-- 1.3.6.1.4.1.19338.19.2.3.16.4
		refusedCount119 OBJECT-TYPE
			SYNTAX OCTET STRING
			MAX-ACCESS read-write
			STATUS current
			DESCRIPTION
				"Description."
			::= { cARDDL1 4 }

		
		-- 1.3.6.1.4.1.19338.19.2.3.17
		cCHLAN1 OBJECT-IDENTITY
			STATUS current
			DESCRIPTION 
				"Description."
			::= { network2 17 }

		
		-- 1.3.6.1.4.1.19338.19.2.3.17.1
		totalINCount120 OBJECT-TYPE
			SYNTAX OCTET STRING
			MAX-ACCESS read-write
			STATUS current
			DESCRIPTION
				"Description."
			::= { cCHLAN1 1 }

		
		-- 1.3.6.1.4.1.19338.19.2.3.17.2
		successCount120 OBJECT-TYPE
			SYNTAX OCTET STRING
			MAX-ACCESS read-write
			STATUS current
			DESCRIPTION
				"Description."
			::= { cCHLAN1 2 }

		
		-- 1.3.6.1.4.1.19338.19.2.3.17.3
		failCount120 OBJECT-TYPE
			SYNTAX OCTET STRING
			MAX-ACCESS read-write
			STATUS current
			DESCRIPTION
				"Description."
			::= { cCHLAN1 3 }

		
		-- 1.3.6.1.4.1.19338.19.2.3.17.4
		refusedCount120 OBJECT-TYPE
			SYNTAX OCTET STRING
			MAX-ACCESS read-write
			STATUS current
			DESCRIPTION
				"Description."
			::= { cCHLAN1 4 }

		
		-- 1.3.6.1.4.1.19338.19.2.3.18
		cDPCR1 OBJECT-IDENTITY
			STATUS current
			DESCRIPTION 
				"Description."
			::= { network2 18 }

		
		-- 1.3.6.1.4.1.19338.19.2.3.18.1
		totalINCount121 OBJECT-TYPE
			SYNTAX OCTET STRING
			MAX-ACCESS read-write
			STATUS current
			DESCRIPTION
				"Description."
			::= { cDPCR1 1 }

		
		-- 1.3.6.1.4.1.19338.19.2.3.18.2
		successCount121 OBJECT-TYPE
			SYNTAX OCTET STRING
			MAX-ACCESS read-write
			STATUS current
			DESCRIPTION
				"Description."
			::= { cDPCR1 2 }

		
		-- 1.3.6.1.4.1.19338.19.2.3.18.3
		failCount121 OBJECT-TYPE
			SYNTAX OCTET STRING
			MAX-ACCESS read-write
			STATUS current
			DESCRIPTION
				"Description."
			::= { cDPCR1 3 }

		
		-- 1.3.6.1.4.1.19338.19.2.3.18.4
		refusedCount121 OBJECT-TYPE
			SYNTAX OCTET STRING
			MAX-ACCESS read-write
			STATUS current
			DESCRIPTION
				"Description."
			::= { cDPCR1 4 }

		
		-- 1.3.6.1.4.1.19338.19.2.3.19
		cGMBALREQ1 OBJECT-IDENTITY
			STATUS current
			DESCRIPTION 
				"Description."
			::= { network2 19 }

		
		-- 1.3.6.1.4.1.19338.19.2.3.19.1
		totalINCount122 OBJECT-TYPE
			SYNTAX OCTET STRING
			MAX-ACCESS read-write
			STATUS current
			DESCRIPTION
				"Description."
			::= { cGMBALREQ1 1 }

		
		-- 1.3.6.1.4.1.19338.19.2.3.19.2
		successCount122 OBJECT-TYPE
			SYNTAX OCTET STRING
			MAX-ACCESS read-write
			STATUS current
			DESCRIPTION
				"Description."
			::= { cGMBALREQ1 2 }

		
		-- 1.3.6.1.4.1.19338.19.2.3.19.3
		failCount122 OBJECT-TYPE
			SYNTAX OCTET STRING
			MAX-ACCESS read-write
			STATUS current
			DESCRIPTION
				"Description."
			::= { cGMBALREQ1 3 }

		
		-- 1.3.6.1.4.1.19338.19.2.3.19.4
		refusedCount122 OBJECT-TYPE
			SYNTAX OCTET STRING
			MAX-ACCESS read-write
			STATUS current
			DESCRIPTION
				"Description."
			::= { cGMBALREQ1 4 }

		
		-- 1.3.6.1.4.1.19338.19.2.3.20
		cHANGELANG1 OBJECT-IDENTITY
			STATUS current
			DESCRIPTION 
				"Description."
			::= { network2 20 }

		
		-- 1.3.6.1.4.1.19338.19.2.3.20.1
		totalINCount123 OBJECT-TYPE
			SYNTAX OCTET STRING
			MAX-ACCESS read-write
			STATUS current
			DESCRIPTION
				"Description."
			::= { cHANGELANG1 1 }

		
		-- 1.3.6.1.4.1.19338.19.2.3.20.2
		successCount123 OBJECT-TYPE
			SYNTAX OCTET STRING
			MAX-ACCESS read-write
			STATUS current
			DESCRIPTION
				"Description."
			::= { cHANGELANG1 2 }

		
		-- 1.3.6.1.4.1.19338.19.2.3.20.3
		failCount123 OBJECT-TYPE
			SYNTAX OCTET STRING
			MAX-ACCESS read-write
			STATUS current
			DESCRIPTION
				"Description."
			::= { cHANGELANG1 3 }

		
		-- 1.3.6.1.4.1.19338.19.2.3.20.4
		refusedCount123 OBJECT-TYPE
			SYNTAX OCTET STRING
			MAX-ACCESS read-write
			STATUS current
			DESCRIPTION
				"Description."
			::= { cHANGELANG1 4 }

		
		-- 1.3.6.1.4.1.19338.19.2.3.21
		cPN1 OBJECT-IDENTITY
			STATUS current
			DESCRIPTION 
				"Description."
			::= { network2 21 }

		
		-- 1.3.6.1.4.1.19338.19.2.3.21.1
		totalINCount124 OBJECT-TYPE
			SYNTAX OCTET STRING
			MAX-ACCESS read-write
			STATUS current
			DESCRIPTION
				"Description."
			::= { cPN1 1 }

		
		-- 1.3.6.1.4.1.19338.19.2.3.21.2
		successCount124 OBJECT-TYPE
			SYNTAX OCTET STRING
			MAX-ACCESS read-write
			STATUS current
			DESCRIPTION
				"Description."
			::= { cPN1 2 }

		
		-- 1.3.6.1.4.1.19338.19.2.3.21.3
		failCount124 OBJECT-TYPE
			SYNTAX OCTET STRING
			MAX-ACCESS read-write
			STATUS current
			DESCRIPTION
				"Description."
			::= { cPN1 3 }

		
		-- 1.3.6.1.4.1.19338.19.2.3.21.4
		refusedCount124 OBJECT-TYPE
			SYNTAX OCTET STRING
			MAX-ACCESS read-write
			STATUS current
			DESCRIPTION
				"Description."
			::= { cPN1 4 }

		
		-- 1.3.6.1.4.1.19338.19.2.3.22
		cPREG1 OBJECT-IDENTITY
			STATUS current
			DESCRIPTION 
				"Description."
			::= { network2 22 }

		
		-- 1.3.6.1.4.1.19338.19.2.3.22.1
		totalINCount125 OBJECT-TYPE
			SYNTAX OCTET STRING
			MAX-ACCESS read-write
			STATUS current
			DESCRIPTION
				"Description."
			::= { cPREG1 1 }

		
		-- 1.3.6.1.4.1.19338.19.2.3.22.2
		successCount125 OBJECT-TYPE
			SYNTAX OCTET STRING
			MAX-ACCESS read-write
			STATUS current
			DESCRIPTION
				"Description."
			::= { cPREG1 2 }

		
		-- 1.3.6.1.4.1.19338.19.2.3.22.3
		failCount125 OBJECT-TYPE
			SYNTAX OCTET STRING
			MAX-ACCESS read-write
			STATUS current
			DESCRIPTION
				"Description."
			::= { cPREG1 3 }

		
		-- 1.3.6.1.4.1.19338.19.2.3.22.4
		refusedCount125 OBJECT-TYPE
			SYNTAX OCTET STRING
			MAX-ACCESS read-write
			STATUS current
			DESCRIPTION
				"Description."
			::= { cPREG1 4 }

		
		-- 1.3.6.1.4.1.19338.19.2.3.23
		cRC1 OBJECT-IDENTITY
			STATUS current
			DESCRIPTION 
				"Description."
			::= { network2 23 }

		
		-- 1.3.6.1.4.1.19338.19.2.3.23.1
		totalINCount126 OBJECT-TYPE
			SYNTAX OCTET STRING
			MAX-ACCESS read-write
			STATUS current
			DESCRIPTION
				"Description."
			::= { cRC1 1 }

		
		-- 1.3.6.1.4.1.19338.19.2.3.23.2
		successCount126 OBJECT-TYPE
			SYNTAX OCTET STRING
			MAX-ACCESS read-write
			STATUS current
			DESCRIPTION
				"Description."
			::= { cRC1 2 }

		
		-- 1.3.6.1.4.1.19338.19.2.3.23.3
		failCount126 OBJECT-TYPE
			SYNTAX OCTET STRING
			MAX-ACCESS read-write
			STATUS current
			DESCRIPTION
				"Description."
			::= { cRC1 3 }

		
		-- 1.3.6.1.4.1.19338.19.2.3.23.4
		refusedCount126 OBJECT-TYPE
			SYNTAX OCTET STRING
			MAX-ACCESS read-write
			STATUS current
			DESCRIPTION
				"Description."
			::= { cRC1 4 }

		
		-- 1.3.6.1.4.1.19338.19.2.3.24
		cUSTXTRF1 OBJECT-IDENTITY
			STATUS current
			DESCRIPTION 
				"Description."
			::= { network2 24 }

		
		-- 1.3.6.1.4.1.19338.19.2.3.24.1
		totalINCount127 OBJECT-TYPE
			SYNTAX OCTET STRING
			MAX-ACCESS read-write
			STATUS current
			DESCRIPTION
				"Description."
			::= { cUSTXTRF1 1 }

		
		-- 1.3.6.1.4.1.19338.19.2.3.24.2
		successCount127 OBJECT-TYPE
			SYNTAX OCTET STRING
			MAX-ACCESS read-write
			STATUS current
			DESCRIPTION
				"Description."
			::= { cUSTXTRF1 2 }

		
		-- 1.3.6.1.4.1.19338.19.2.3.24.3
		failCount127 OBJECT-TYPE
			SYNTAX OCTET STRING
			MAX-ACCESS read-write
			STATUS current
			DESCRIPTION
				"Description."
			::= { cUSTXTRF1 3 }

		
		-- 1.3.6.1.4.1.19338.19.2.3.24.4
		refusedCount127 OBJECT-TYPE
			SYNTAX OCTET STRING
			MAX-ACCESS read-write
			STATUS current
			DESCRIPTION
				"Description."
			::= { cUSTXTRF1 4 }

		
		-- 1.3.6.1.4.1.19338.19.2.3.25
		dELREGSUBS1 OBJECT-IDENTITY
			STATUS current
			DESCRIPTION 
				"Description."
			::= { network2 25 }

		
		-- 1.3.6.1.4.1.19338.19.2.3.25.1
		totalINCount128 OBJECT-TYPE
			SYNTAX OCTET STRING
			MAX-ACCESS read-write
			STATUS current
			DESCRIPTION
				"Description."
			::= { dELREGSUBS1 1 }

		
		-- 1.3.6.1.4.1.19338.19.2.3.25.2
		successCount128 OBJECT-TYPE
			SYNTAX OCTET STRING
			MAX-ACCESS read-write
			STATUS current
			DESCRIPTION
				"Description."
			::= { dELREGSUBS1 2 }

		
		-- 1.3.6.1.4.1.19338.19.2.3.25.3
		failCount128 OBJECT-TYPE
			SYNTAX OCTET STRING
			MAX-ACCESS read-write
			STATUS current
			DESCRIPTION
				"Description."
			::= { dELREGSUBS1 3 }

		
		-- 1.3.6.1.4.1.19338.19.2.3.25.4
		refusedCount128 OBJECT-TYPE
			SYNTAX OCTET STRING
			MAX-ACCESS read-write
			STATUS current
			DESCRIPTION
				"Description."
			::= { dELREGSUBS1 4 }

		
		-- 1.3.6.1.4.1.19338.19.2.3.26
		dELSID1 OBJECT-IDENTITY
			STATUS current
			DESCRIPTION 
				"Description."
			::= { network2 26 }

		
		-- 1.3.6.1.4.1.19338.19.2.3.26.1
		totalINCount129 OBJECT-TYPE
			SYNTAX OCTET STRING
			MAX-ACCESS read-write
			STATUS current
			DESCRIPTION
				"Description."
			::= { dELSID1 1 }

		
		-- 1.3.6.1.4.1.19338.19.2.3.26.2
		successCount129 OBJECT-TYPE
			SYNTAX OCTET STRING
			MAX-ACCESS read-write
			STATUS current
			DESCRIPTION
				"Description."
			::= { dELSID1 2 }

		
		-- 1.3.6.1.4.1.19338.19.2.3.26.3
		failCount129 OBJECT-TYPE
			SYNTAX OCTET STRING
			MAX-ACCESS read-write
			STATUS current
			DESCRIPTION
				"Description."
			::= { dELSID1 3 }

		
		-- 1.3.6.1.4.1.19338.19.2.3.26.4
		refusedCount129 OBJECT-TYPE
			SYNTAX OCTET STRING
			MAX-ACCESS read-write
			STATUS current
			DESCRIPTION
				"Description."
			::= { dELSID1 4 }

		
		-- 1.3.6.1.4.1.19338.19.2.3.27
		dRCRTRF1 OBJECT-IDENTITY
			STATUS current
			DESCRIPTION 
				"Description."
			::= { network2 27 }

		
		-- 1.3.6.1.4.1.19338.19.2.3.27.1
		totalINCount130 OBJECT-TYPE
			SYNTAX OCTET STRING
			MAX-ACCESS read-write
			STATUS current
			DESCRIPTION
				"Description."
			::= { dRCRTRF1 1 }

		
		-- 1.3.6.1.4.1.19338.19.2.3.27.2
		successCount130 OBJECT-TYPE
			SYNTAX OCTET STRING
			MAX-ACCESS read-write
			STATUS current
			DESCRIPTION
				"Description."
			::= { dRCRTRF1 2 }

		
		-- 1.3.6.1.4.1.19338.19.2.3.27.3
		failCount130 OBJECT-TYPE
			SYNTAX OCTET STRING
			MAX-ACCESS read-write
			STATUS current
			DESCRIPTION
				"Description."
			::= { dRCRTRF1 3 }

		
		-- 1.3.6.1.4.1.19338.19.2.3.27.4
		refusedCount130 OBJECT-TYPE
			SYNTAX OCTET STRING
			MAX-ACCESS read-write
			STATUS current
			DESCRIPTION
				"Description."
			::= { dRCRTRF1 4 }

		
		-- 1.3.6.1.4.1.19338.19.2.3.28
		eNQSID1 OBJECT-IDENTITY
			STATUS current
			DESCRIPTION 
				"Description."
			::= { network2 28 }

		
		-- 1.3.6.1.4.1.19338.19.2.3.28.1
		totalINCount131 OBJECT-TYPE
			SYNTAX OCTET STRING
			MAX-ACCESS read-write
			STATUS current
			DESCRIPTION
				"Description."
			::= { eNQSID1 1 }

		
		-- 1.3.6.1.4.1.19338.19.2.3.28.2
		successCount131 OBJECT-TYPE
			SYNTAX OCTET STRING
			MAX-ACCESS read-write
			STATUS current
			DESCRIPTION
				"Description."
			::= { eNQSID1 2 }

		
		-- 1.3.6.1.4.1.19338.19.2.3.28.3
		failCount131 OBJECT-TYPE
			SYNTAX OCTET STRING
			MAX-ACCESS read-write
			STATUS current
			DESCRIPTION
				"Description."
			::= { eNQSID1 3 }

		
		-- 1.3.6.1.4.1.19338.19.2.3.28.4
		refusedCount131 OBJECT-TYPE
			SYNTAX OCTET STRING
			MAX-ACCESS read-write
			STATUS current
			DESCRIPTION
				"Description."
			::= { eNQSID1 4 }

		
		-- 1.3.6.1.4.1.19338.19.2.3.29
		eVD1 OBJECT-IDENTITY
			STATUS current
			DESCRIPTION 
				"Description."
			::= { network2 29 }

		
		-- 1.3.6.1.4.1.19338.19.2.3.29.1
		totalINCount132 OBJECT-TYPE
			SYNTAX OCTET STRING
			MAX-ACCESS read-write
			STATUS current
			DESCRIPTION
				"Description."
			::= { eVD1 1 }

		
		-- 1.3.6.1.4.1.19338.19.2.3.29.2
		successCount132 OBJECT-TYPE
			SYNTAX OCTET STRING
			MAX-ACCESS read-write
			STATUS current
			DESCRIPTION
				"Description."
			::= { eVD1 2 }

		
		-- 1.3.6.1.4.1.19338.19.2.3.29.3
		failCount132 OBJECT-TYPE
			SYNTAX OCTET STRING
			MAX-ACCESS read-write
			STATUS current
			DESCRIPTION
				"Description."
			::= { eVD1 3 }

		
		-- 1.3.6.1.4.1.19338.19.2.3.29.4
		refusedCount132 OBJECT-TYPE
			SYNTAX OCTET STRING
			MAX-ACCESS read-write
			STATUS current
			DESCRIPTION
				"Description."
			::= { eVD1 4 }

		
		-- 1.3.6.1.4.1.19338.19.2.3.30
		eVR1 OBJECT-IDENTITY
			STATUS current
			DESCRIPTION 
				"Description."
			::= { network2 30 }

		
		-- 1.3.6.1.4.1.19338.19.2.3.30.1
		totalINCount133 OBJECT-TYPE
			SYNTAX OCTET STRING
			MAX-ACCESS read-write
			STATUS current
			DESCRIPTION
				"Description."
			::= { eVR1 1 }

		
		-- 1.3.6.1.4.1.19338.19.2.3.30.2
		successCount133 OBJECT-TYPE
			SYNTAX OCTET STRING
			MAX-ACCESS read-write
			STATUS current
			DESCRIPTION
				"Description."
			::= { eVR1 2 }

		
		-- 1.3.6.1.4.1.19338.19.2.3.30.3
		failCount133 OBJECT-TYPE
			SYNTAX OCTET STRING
			MAX-ACCESS read-write
			STATUS current
			DESCRIPTION
				"Description."
			::= { eVR1 3 }

		
		-- 1.3.6.1.4.1.19338.19.2.3.30.4
		refusedCount133 OBJECT-TYPE
			SYNTAX OCTET STRING
			MAX-ACCESS read-write
			STATUS current
			DESCRIPTION
				"Description."
			::= { eVR1 4 }

		
		-- 1.3.6.1.4.1.19338.19.2.3.31
		eXTGRPH1 OBJECT-IDENTITY
			STATUS current
			DESCRIPTION 
				"Description."
			::= { network2 31 }

		
		-- 1.3.6.1.4.1.19338.19.2.3.31.1
		totalINCount134 OBJECT-TYPE
			SYNTAX OCTET STRING
			MAX-ACCESS read-write
			STATUS current
			DESCRIPTION
				"Description."
			::= { eXTGRPH1 1 }

		
		-- 1.3.6.1.4.1.19338.19.2.3.31.2
		successCount134 OBJECT-TYPE
			SYNTAX OCTET STRING
			MAX-ACCESS read-write
			STATUS current
			DESCRIPTION
				"Description."
			::= { eXTGRPH1 2 }

		
		-- 1.3.6.1.4.1.19338.19.2.3.31.3
		failCount134 OBJECT-TYPE
			SYNTAX OCTET STRING
			MAX-ACCESS read-write
			STATUS current
			DESCRIPTION
				"Description."
			::= { eXTGRPH1 3 }

		
		-- 1.3.6.1.4.1.19338.19.2.3.31.4
		refusedCount134 OBJECT-TYPE
			SYNTAX OCTET STRING
			MAX-ACCESS read-write
			STATUS current
			DESCRIPTION
				"Description."
			::= { eXTGRPH1 4 }

		
		-- 1.3.6.1.4.1.19338.19.2.3.32
		eXTSUSRES1 OBJECT-IDENTITY
			STATUS current
			DESCRIPTION 
				"Description."
			::= { network2 32 }

		
		-- 1.3.6.1.4.1.19338.19.2.3.32.1
		totalINCount135 OBJECT-TYPE
			SYNTAX OCTET STRING
			MAX-ACCESS read-write
			STATUS current
			DESCRIPTION
				"Description."
			::= { eXTSUSRES1 1 }

		
		-- 1.3.6.1.4.1.19338.19.2.3.32.2
		successCount135 OBJECT-TYPE
			SYNTAX OCTET STRING
			MAX-ACCESS read-write
			STATUS current
			DESCRIPTION
				"Description."
			::= { eXTSUSRES1 2 }

		
		-- 1.3.6.1.4.1.19338.19.2.3.32.3
		failCount135 OBJECT-TYPE
			SYNTAX OCTET STRING
			MAX-ACCESS read-write
			STATUS current
			DESCRIPTION
				"Description."
			::= { eXTSUSRES1 3 }

		
		-- 1.3.6.1.4.1.19338.19.2.3.32.4
		refusedCount135 OBJECT-TYPE
			SYNTAX OCTET STRING
			MAX-ACCESS read-write
			STATUS current
			DESCRIPTION
				"Description."
			::= { eXTSUSRES1 4 }

		
		-- 1.3.6.1.4.1.19338.19.2.3.33
		eXTUSRADD1 OBJECT-IDENTITY
			STATUS current
			DESCRIPTION 
				"Description."
			::= { network2 33 }

		
		-- 1.3.6.1.4.1.19338.19.2.3.33.1
		totalINCount136 OBJECT-TYPE
			SYNTAX OCTET STRING
			MAX-ACCESS read-write
			STATUS current
			DESCRIPTION
				"Description."
			::= { eXTUSRADD1 1 }

		
		-- 1.3.6.1.4.1.19338.19.2.3.33.2
		successCount136 OBJECT-TYPE
			SYNTAX OCTET STRING
			MAX-ACCESS read-write
			STATUS current
			DESCRIPTION
				"Description."
			::= { eXTUSRADD1 2 }

		
		-- 1.3.6.1.4.1.19338.19.2.3.33.3
		failCount136 OBJECT-TYPE
			SYNTAX OCTET STRING
			MAX-ACCESS read-write
			STATUS current
			DESCRIPTION
				"Description."
			::= { eXTUSRADD1 3 }

		
		-- 1.3.6.1.4.1.19338.19.2.3.33.4
		refusedCount136 OBJECT-TYPE
			SYNTAX OCTET STRING
			MAX-ACCESS read-write
			STATUS current
			DESCRIPTION
				"Description."
			::= { eXTUSRADD1 4 }

		
		-- 1.3.6.1.4.1.19338.19.2.3.34
		iCCIDMSISD1 OBJECT-IDENTITY
			STATUS current
			DESCRIPTION 
				"Description."
			::= { network2 34 }

		
		-- 1.3.6.1.4.1.19338.19.2.3.34.1
		totalINCount137 OBJECT-TYPE
			SYNTAX OCTET STRING
			MAX-ACCESS read-write
			STATUS current
			DESCRIPTION
				"Description."
			::= { iCCIDMSISD1 1 }

		
		-- 1.3.6.1.4.1.19338.19.2.3.34.2
		successCount137 OBJECT-TYPE
			SYNTAX OCTET STRING
			MAX-ACCESS read-write
			STATUS current
			DESCRIPTION
				"Description."
			::= { iCCIDMSISD1 2 }

		
		-- 1.3.6.1.4.1.19338.19.2.3.34.3
		failCount137 OBJECT-TYPE
			SYNTAX OCTET STRING
			MAX-ACCESS read-write
			STATUS current
			DESCRIPTION
				"Description."
			::= { iCCIDMSISD1 3 }

		
		-- 1.3.6.1.4.1.19338.19.2.3.34.4
		refusedCount137 OBJECT-TYPE
			SYNTAX OCTET STRING
			MAX-ACCESS read-write
			STATUS current
			DESCRIPTION
				"Description."
			::= { iCCIDMSISD1 4 }

		
		-- 1.3.6.1.4.1.19338.19.2.3.35
		iNENQREQ1 OBJECT-IDENTITY
			STATUS current
			DESCRIPTION 
				"Description."
			::= { network2 35 }

		
		-- 1.3.6.1.4.1.19338.19.2.3.35.1
		totalINCount138 OBJECT-TYPE
			SYNTAX OCTET STRING
			MAX-ACCESS read-write
			STATUS current
			DESCRIPTION
				"Description."
			::= { iNENQREQ1 1 }

		
		-- 1.3.6.1.4.1.19338.19.2.3.35.2
		successCount138 OBJECT-TYPE
			SYNTAX OCTET STRING
			MAX-ACCESS read-write
			STATUS current
			DESCRIPTION
				"Description."
			::= { iNENQREQ1 2 }

		
		-- 1.3.6.1.4.1.19338.19.2.3.35.3
		failCount138 OBJECT-TYPE
			SYNTAX OCTET STRING
			MAX-ACCESS read-write
			STATUS current
			DESCRIPTION
				"Description."
			::= { iNENQREQ1 3 }

		
		-- 1.3.6.1.4.1.19338.19.2.3.35.4
		refusedCount138 OBJECT-TYPE
			SYNTAX OCTET STRING
			MAX-ACCESS read-write
			STATUS current
			DESCRIPTION
				"Description."
			::= { iNENQREQ1 4 }

		
		-- 1.3.6.1.4.1.19338.19.2.3.36
		iNTRRC1 OBJECT-IDENTITY
			STATUS current
			DESCRIPTION 
				"Description."
			::= { network2 36 }

		
		-- 1.3.6.1.4.1.19338.19.2.3.36.1
		totalINCount139 OBJECT-TYPE
			SYNTAX OCTET STRING
			MAX-ACCESS read-write
			STATUS current
			DESCRIPTION
				"Description."
			::= { iNTRRC1 1 }

		
		-- 1.3.6.1.4.1.19338.19.2.3.36.2
		successCount139 OBJECT-TYPE
			SYNTAX OCTET STRING
			MAX-ACCESS read-write
			STATUS current
			DESCRIPTION
				"Description."
			::= { iNTRRC1 2 }

		
		-- 1.3.6.1.4.1.19338.19.2.3.36.3
		failCount139 OBJECT-TYPE
			SYNTAX OCTET STRING
			MAX-ACCESS read-write
			STATUS current
			DESCRIPTION
				"Description."
			::= { iNTRRC1 3 }

		
		-- 1.3.6.1.4.1.19338.19.2.3.36.4
		refusedCount139 OBJECT-TYPE
			SYNTAX OCTET STRING
			MAX-ACCESS read-write
			STATUS current
			DESCRIPTION
				"Description."
			::= { iNTRRC1 4 }

		
		-- 1.3.6.1.4.1.19338.19.2.3.37
		iR1 OBJECT-IDENTITY
			STATUS current
			DESCRIPTION 
				"Description."
			::= { network2 37 }

		
		-- 1.3.6.1.4.1.19338.19.2.3.37.1
		totalINCount140 OBJECT-TYPE
			SYNTAX OCTET STRING
			MAX-ACCESS read-write
			STATUS current
			DESCRIPTION
				"Description."
			::= { iR1 1 }

		
		-- 1.3.6.1.4.1.19338.19.2.3.37.2
		successCount140 OBJECT-TYPE
			SYNTAX OCTET STRING
			MAX-ACCESS read-write
			STATUS current
			DESCRIPTION
				"Description."
			::= { iR1 2 }

		
		-- 1.3.6.1.4.1.19338.19.2.3.37.3
		failCount140 OBJECT-TYPE
			SYNTAX OCTET STRING
			MAX-ACCESS read-write
			STATUS current
			DESCRIPTION
				"Description."
			::= { iR1 3 }

		
		-- 1.3.6.1.4.1.19338.19.2.3.37.4
		refusedCount140 OBJECT-TYPE
			SYNTAX OCTET STRING
			MAX-ACCESS read-write
			STATUS current
			DESCRIPTION
				"Description."
			::= { iR1 4 }

		
		-- 1.3.6.1.4.1.19338.19.2.3.38
		lASTXTRF1 OBJECT-IDENTITY
			STATUS current
			DESCRIPTION 
				"Description."
			::= { network2 38 }

		
		-- 1.3.6.1.4.1.19338.19.2.3.38.1
		totalINCount141 OBJECT-TYPE
			SYNTAX OCTET STRING
			MAX-ACCESS read-write
			STATUS current
			DESCRIPTION
				"Description."
			::= { lASTXTRF1 1 }

		
		-- 1.3.6.1.4.1.19338.19.2.3.38.2
		successCount141 OBJECT-TYPE
			SYNTAX OCTET STRING
			MAX-ACCESS read-write
			STATUS current
			DESCRIPTION
				"Description."
			::= { lASTXTRF1 2 }

		
		-- 1.3.6.1.4.1.19338.19.2.3.38.3
		failCount141 OBJECT-TYPE
			SYNTAX OCTET STRING
			MAX-ACCESS read-write
			STATUS current
			DESCRIPTION
				"Description."
			::= { lASTXTRF1 3 }

		
		-- 1.3.6.1.4.1.19338.19.2.3.38.4
		refusedCount141 OBJECT-TYPE
			SYNTAX OCTET STRING
			MAX-ACCESS read-write
			STATUS current
			DESCRIPTION
				"Description."
			::= { lASTXTRF1 4 }

		
		-- 1.3.6.1.4.1.19338.19.2.3.39
		lMBDBT1 OBJECT-IDENTITY
			STATUS current
			DESCRIPTION 
				"Description."
			::= { network2 39 }

		
		-- 1.3.6.1.4.1.19338.19.2.3.39.1
		totalINCount142 OBJECT-TYPE
			SYNTAX OCTET STRING
			MAX-ACCESS read-write
			STATUS current
			DESCRIPTION
				"Description."
			::= { lMBDBT1 1 }

		
		-- 1.3.6.1.4.1.19338.19.2.3.39.2
		successCount142 OBJECT-TYPE
			SYNTAX OCTET STRING
			MAX-ACCESS read-write
			STATUS current
			DESCRIPTION
				"Description."
			::= { lMBDBT1 2 }

		
		-- 1.3.6.1.4.1.19338.19.2.3.39.3
		failCount142 OBJECT-TYPE
			SYNTAX OCTET STRING
			MAX-ACCESS read-write
			STATUS current
			DESCRIPTION
				"Description."
			::= { lMBDBT1 3 }

		
		-- 1.3.6.1.4.1.19338.19.2.3.39.4
		refusedCount142 OBJECT-TYPE
			SYNTAX OCTET STRING
			MAX-ACCESS read-write
			STATUS current
			DESCRIPTION
				"Description."
			::= { lMBDBT1 4 }

		
		-- 1.3.6.1.4.1.19338.19.2.3.40
		mCDL1 OBJECT-IDENTITY
			STATUS current
			DESCRIPTION 
				"Description."
			::= { network2 40 }

		
		-- 1.3.6.1.4.1.19338.19.2.3.40.1
		totalINCount143 OBJECT-TYPE
			SYNTAX OCTET STRING
			MAX-ACCESS read-write
			STATUS current
			DESCRIPTION
				"Description."
			::= { mCDL1 1 }

		
		-- 1.3.6.1.4.1.19338.19.2.3.40.2
		successCount143 OBJECT-TYPE
			SYNTAX OCTET STRING
			MAX-ACCESS read-write
			STATUS current
			DESCRIPTION
				"Description."
			::= { mCDL1 2 }

		
		-- 1.3.6.1.4.1.19338.19.2.3.40.3
		failCount143 OBJECT-TYPE
			SYNTAX OCTET STRING
			MAX-ACCESS read-write
			STATUS current
			DESCRIPTION
				"Description."
			::= { mCDL1 3 }

		
		-- 1.3.6.1.4.1.19338.19.2.3.40.4
		refusedCount143 OBJECT-TYPE
			SYNTAX OCTET STRING
			MAX-ACCESS read-write
			STATUS current
			DESCRIPTION
				"Description."
			::= { mCDL1 4 }

		
		-- 1.3.6.1.4.1.19338.19.2.3.41
		mCDLR1 OBJECT-IDENTITY
			STATUS current
			DESCRIPTION 
				"Description."
			::= { network2 41 }

		
		-- 1.3.6.1.4.1.19338.19.2.3.41.1
		totalINCount144 OBJECT-TYPE
			SYNTAX OCTET STRING
			MAX-ACCESS read-write
			STATUS current
			DESCRIPTION
				"Description."
			::= { mCDLR1 1 }

		
		-- 1.3.6.1.4.1.19338.19.2.3.41.2
		successCount144 OBJECT-TYPE
			SYNTAX OCTET STRING
			MAX-ACCESS read-write
			STATUS current
			DESCRIPTION
				"Description."
			::= { mCDLR1 2 }

		
		-- 1.3.6.1.4.1.19338.19.2.3.41.3
		failCount144 OBJECT-TYPE
			SYNTAX OCTET STRING
			MAX-ACCESS read-write
			STATUS current
			DESCRIPTION
				"Description."
			::= { mCDLR1 3 }

		
		-- 1.3.6.1.4.1.19338.19.2.3.41.4
		refusedCount144 OBJECT-TYPE
			SYNTAX OCTET STRING
			MAX-ACCESS read-write
			STATUS current
			DESCRIPTION
				"Description."
			::= { mCDLR1 4 }

		
		-- 1.3.6.1.4.1.19338.19.2.3.42
		mCDLV1 OBJECT-IDENTITY
			STATUS current
			DESCRIPTION 
				"Description."
			::= { network2 42 }

		
		-- 1.3.6.1.4.1.19338.19.2.3.42.1
		totalINCount145 OBJECT-TYPE
			SYNTAX OCTET STRING
			MAX-ACCESS read-write
			STATUS current
			DESCRIPTION
				"Description."
			::= { mCDLV1 1 }

		
		-- 1.3.6.1.4.1.19338.19.2.3.42.2
		successCount145 OBJECT-TYPE
			SYNTAX OCTET STRING
			MAX-ACCESS read-write
			STATUS current
			DESCRIPTION
				"Description."
			::= { mCDLV1 2 }

		
		-- 1.3.6.1.4.1.19338.19.2.3.42.3
		failCount145 OBJECT-TYPE
			SYNTAX OCTET STRING
			MAX-ACCESS read-write
			STATUS current
			DESCRIPTION
				"Description."
			::= { mCDLV1 3 }

		
		-- 1.3.6.1.4.1.19338.19.2.3.42.4
		refusedCount145 OBJECT-TYPE
			SYNTAX OCTET STRING
			MAX-ACCESS read-write
			STATUS current
			DESCRIPTION
				"Description."
			::= { mCDLV1 4 }

		
		-- 1.3.6.1.4.1.19338.19.2.3.43
		mNPUPLOAD1 OBJECT-IDENTITY
			STATUS current
			DESCRIPTION 
				"Description."
			::= { network2 43 }

		
		-- 1.3.6.1.4.1.19338.19.2.3.43.1
		totalINCount146 OBJECT-TYPE
			SYNTAX OCTET STRING
			MAX-ACCESS read-write
			STATUS current
			DESCRIPTION
				"Description."
			::= { mNPUPLOAD1 1 }

		
		-- 1.3.6.1.4.1.19338.19.2.3.43.2
		successCount146 OBJECT-TYPE
			SYNTAX OCTET STRING
			MAX-ACCESS read-write
			STATUS current
			DESCRIPTION
				"Description."
			::= { mNPUPLOAD1 2 }

		
		-- 1.3.6.1.4.1.19338.19.2.3.43.3
		failCount146 OBJECT-TYPE
			SYNTAX OCTET STRING
			MAX-ACCESS read-write
			STATUS current
			DESCRIPTION
				"Description."
			::= { mNPUPLOAD1 3 }

		
		-- 1.3.6.1.4.1.19338.19.2.3.43.4
		refusedCount146 OBJECT-TYPE
			SYNTAX OCTET STRING
			MAX-ACCESS read-write
			STATUS current
			DESCRIPTION
				"Description."
			::= { mNPUPLOAD1 4 }

		
		-- 1.3.6.1.4.1.19338.19.2.3.44
		multDEL1 OBJECT-IDENTITY
			STATUS current
			DESCRIPTION 
				"Description."
			::= { network2 44 }

		
		-- 1.3.6.1.4.1.19338.19.2.3.44.1
		totalINCount147 OBJECT-TYPE
			SYNTAX OCTET STRING
			MAX-ACCESS read-write
			STATUS current
			DESCRIPTION
				"Description."
			::= { multDEL1 1 }

		
		-- 1.3.6.1.4.1.19338.19.2.3.44.2
		successCount147 OBJECT-TYPE
			SYNTAX OCTET STRING
			MAX-ACCESS read-write
			STATUS current
			DESCRIPTION
				"Description."
			::= { multDEL1 2 }

		
		-- 1.3.6.1.4.1.19338.19.2.3.44.3
		failCount147 OBJECT-TYPE
			SYNTAX OCTET STRING
			MAX-ACCESS read-write
			STATUS current
			DESCRIPTION
				"Description."
			::= { multDEL1 3 }

		
		-- 1.3.6.1.4.1.19338.19.2.3.44.4
		refusedCount147 OBJECT-TYPE
			SYNTAX OCTET STRING
			MAX-ACCESS read-write
			STATUS current
			DESCRIPTION
				"Description."
			::= { multDEL1 4 }

		
		-- 1.3.6.1.4.1.19338.19.2.3.45
		mvd1 OBJECT-IDENTITY
			STATUS current
			DESCRIPTION 
				"Description."
			::= { network2 45 }

		
		-- 1.3.6.1.4.1.19338.19.2.3.45.1
		totalINCount148 OBJECT-TYPE
			SYNTAX OCTET STRING
			MAX-ACCESS read-write
			STATUS current
			DESCRIPTION
				"Description."
			::= { mvd1 1 }

		
		-- 1.3.6.1.4.1.19338.19.2.3.45.2
		successCount148 OBJECT-TYPE
			SYNTAX OCTET STRING
			MAX-ACCESS read-write
			STATUS current
			DESCRIPTION
				"Description."
			::= { mvd1 2 }

		
		-- 1.3.6.1.4.1.19338.19.2.3.45.3
		failCount148 OBJECT-TYPE
			SYNTAX OCTET STRING
			MAX-ACCESS read-write
			STATUS current
			DESCRIPTION
				"Description."
			::= { mvd1 3 }

		
		-- 1.3.6.1.4.1.19338.19.2.3.45.4
		refusedCount148 OBJECT-TYPE
			SYNTAX OCTET STRING
			MAX-ACCESS read-write
			STATUS current
			DESCRIPTION
				"Description."
			::= { mvd1 4 }

		
		-- 1.3.6.1.4.1.19338.19.2.3.46
		o2cIN1 OBJECT-IDENTITY
			STATUS current
			DESCRIPTION 
				"Description."
			::= { network2 46 }

		
		-- 1.3.6.1.4.1.19338.19.2.3.46.1
		totalINCount149 OBJECT-TYPE
			SYNTAX OCTET STRING
			MAX-ACCESS read-write
			STATUS current
			DESCRIPTION
				"Description."
			::= { o2cIN1 1 }

		
		-- 1.3.6.1.4.1.19338.19.2.3.46.2
		successCount149 OBJECT-TYPE
			SYNTAX OCTET STRING
			MAX-ACCESS read-write
			STATUS current
			DESCRIPTION
				"Description."
			::= { o2cIN1 2 }

		
		-- 1.3.6.1.4.1.19338.19.2.3.46.3
		failCount149 OBJECT-TYPE
			SYNTAX OCTET STRING
			MAX-ACCESS read-write
			STATUS current
			DESCRIPTION
				"Description."
			::= { o2cIN1 3 }

		
		-- 1.3.6.1.4.1.19338.19.2.3.46.4
		refusedCount149 OBJECT-TYPE
			SYNTAX OCTET STRING
			MAX-ACCESS read-write
			STATUS current
			DESCRIPTION
				"Description."
			::= { o2cIN1 4 }

		
		-- 1.3.6.1.4.1.19338.19.2.3.47
		o2cINTR1 OBJECT-IDENTITY
			STATUS current
			DESCRIPTION 
				"Description."
			::= { network2 47 }

		
		-- 1.3.6.1.4.1.19338.19.2.3.47.1
		totalINCount150 OBJECT-TYPE
			SYNTAX OCTET STRING
			MAX-ACCESS read-write
			STATUS current
			DESCRIPTION
				"Description."
			::= { o2cINTR1 1 }

		
		-- 1.3.6.1.4.1.19338.19.2.3.47.2
		successCount150 OBJECT-TYPE
			SYNTAX OCTET STRING
			MAX-ACCESS read-write
			STATUS current
			DESCRIPTION
				"Description."
			::= { o2cINTR1 2 }

		
		-- 1.3.6.1.4.1.19338.19.2.3.47.3
		failCount150 OBJECT-TYPE
			SYNTAX OCTET STRING
			MAX-ACCESS read-write
			STATUS current
			DESCRIPTION
				"Description."
			::= { o2cINTR1 3 }

		
		-- 1.3.6.1.4.1.19338.19.2.3.47.4
		refusedCount150 OBJECT-TYPE
			SYNTAX OCTET STRING
			MAX-ACCESS read-write
			STATUS current
			DESCRIPTION
				"Description."
			::= { o2cINTR1 4 }

		
		-- 1.3.6.1.4.1.19338.19.2.3.48
		o2cRET1 OBJECT-IDENTITY
			STATUS current
			DESCRIPTION 
				"Description."
			::= { network2 48 }

		
		-- 1.3.6.1.4.1.19338.19.2.3.48.1
		totalINCount151 OBJECT-TYPE
			SYNTAX OCTET STRING
			MAX-ACCESS read-write
			STATUS current
			DESCRIPTION
				"Description."
			::= { o2cRET1 1 }

		
		-- 1.3.6.1.4.1.19338.19.2.3.48.2
		successCount151 OBJECT-TYPE
			SYNTAX OCTET STRING
			MAX-ACCESS read-write
			STATUS current
			DESCRIPTION
				"Description."
			::= { o2cRET1 2 }

		
		-- 1.3.6.1.4.1.19338.19.2.3.48.3
		failCount151 OBJECT-TYPE
			SYNTAX OCTET STRING
			MAX-ACCESS read-write
			STATUS current
			DESCRIPTION
				"Description."
			::= { o2cRET1 3 }

		
		-- 1.3.6.1.4.1.19338.19.2.3.48.4
		refusedCount151 OBJECT-TYPE
			SYNTAX OCTET STRING
			MAX-ACCESS read-write
			STATUS current
			DESCRIPTION
				"Description."
			::= { o2cRET1 4 }

		
		-- 1.3.6.1.4.1.19338.19.2.3.49
		o2cWD1 OBJECT-IDENTITY
			STATUS current
			DESCRIPTION 
				"Description."
			::= { network2 49 }

		
		-- 1.3.6.1.4.1.19338.19.2.3.49.1
		totalINCount152 OBJECT-TYPE
			SYNTAX OCTET STRING
			MAX-ACCESS read-write
			STATUS current
			DESCRIPTION
				"Description."
			::= { o2cWD1 1 }

		
		-- 1.3.6.1.4.1.19338.19.2.3.49.2
		successCount152 OBJECT-TYPE
			SYNTAX OCTET STRING
			MAX-ACCESS read-write
			STATUS current
			DESCRIPTION
				"Description."
			::= { o2cWD1 2 }

		
		-- 1.3.6.1.4.1.19338.19.2.3.49.3
		failCount152 OBJECT-TYPE
			SYNTAX OCTET STRING
			MAX-ACCESS read-write
			STATUS current
			DESCRIPTION
				"Description."
			::= { o2cWD1 3 }

		
		-- 1.3.6.1.4.1.19338.19.2.3.49.4
		refusedCount152 OBJECT-TYPE
			SYNTAX OCTET STRING
			MAX-ACCESS read-write
			STATUS current
			DESCRIPTION
				"Description."
			::= { o2cWD1 4 }

		
		-- 1.3.6.1.4.1.19338.19.2.3.50
		ordc1 OBJECT-IDENTITY
			STATUS current
			DESCRIPTION 
				"Description."
			::= { network2 50 }

		
		-- 1.3.6.1.4.1.19338.19.2.3.50.1
		totalINCount153 OBJECT-TYPE
			SYNTAX OCTET STRING
			MAX-ACCESS read-write
			STATUS current
			DESCRIPTION
				"Description."
			::= { ordc1 1 }

		
		-- 1.3.6.1.4.1.19338.19.2.3.50.2
		successCount153 OBJECT-TYPE
			SYNTAX OCTET STRING
			MAX-ACCESS read-write
			STATUS current
			DESCRIPTION
				"Description."
			::= { ordc1 2 }

		
		-- 1.3.6.1.4.1.19338.19.2.3.50.3
		failCount153 OBJECT-TYPE
			SYNTAX OCTET STRING
			MAX-ACCESS read-write
			STATUS current
			DESCRIPTION
				"Description."
			::= { ordc1 3 }

		
		-- 1.3.6.1.4.1.19338.19.2.3.50.4
		refusedCount153 OBJECT-TYPE
			SYNTAX OCTET STRING
			MAX-ACCESS read-write
			STATUS current
			DESCRIPTION
				"Description."
			::= { ordc1 4 }

		
		-- 1.3.6.1.4.1.19338.19.2.3.51
		ordl1 OBJECT-IDENTITY
			STATUS current
			DESCRIPTION 
				"Description."
			::= { network2 51 }

		
		-- 1.3.6.1.4.1.19338.19.2.3.51.1
		totalINCount154 OBJECT-TYPE
			SYNTAX OCTET STRING
			MAX-ACCESS read-write
			STATUS current
			DESCRIPTION
				"Description."
			::= { ordl1 1 }

		
		-- 1.3.6.1.4.1.19338.19.2.3.51.2
		successCount154 OBJECT-TYPE
			SYNTAX OCTET STRING
			MAX-ACCESS read-write
			STATUS current
			DESCRIPTION
				"Description."
			::= { ordl1 2 }

		
		-- 1.3.6.1.4.1.19338.19.2.3.51.3
		failCount154 OBJECT-TYPE
			SYNTAX OCTET STRING
			MAX-ACCESS read-write
			STATUS current
			DESCRIPTION
				"Description."
			::= { ordl1 3 }

		
		-- 1.3.6.1.4.1.19338.19.2.3.51.4
		refusedCount154 OBJECT-TYPE
			SYNTAX OCTET STRING
			MAX-ACCESS read-write
			STATUS current
			DESCRIPTION
				"Description."
			::= { ordl1 4 }

		
		-- 1.3.6.1.4.1.19338.19.2.3.52
		otherBALAN1 OBJECT-IDENTITY
			STATUS current
			DESCRIPTION 
				"Description."
			::= { network2 52 }

		
		-- 1.3.6.1.4.1.19338.19.2.3.52.1
		totalINCount155 OBJECT-TYPE
			SYNTAX OCTET STRING
			MAX-ACCESS read-write
			STATUS current
			DESCRIPTION
				"Description."
			::= { otherBALAN1 1 }

		
		-- 1.3.6.1.4.1.19338.19.2.3.52.2
		successCount155 OBJECT-TYPE
			SYNTAX OCTET STRING
			MAX-ACCESS read-write
			STATUS current
			DESCRIPTION
				"Description."
			::= { otherBALAN1 2 }

		
		-- 1.3.6.1.4.1.19338.19.2.3.52.3
		failCount155 OBJECT-TYPE
			SYNTAX OCTET STRING
			MAX-ACCESS read-write
			STATUS current
			DESCRIPTION
				"Description."
			::= { otherBALAN1 3 }

		
		-- 1.3.6.1.4.1.19338.19.2.3.52.4
		refusedCount155 OBJECT-TYPE
			SYNTAX OCTET STRING
			MAX-ACCESS read-write
			STATUS current
			DESCRIPTION
				"Description."
			::= { otherBALAN1 4 }

		
		-- 1.3.6.1.4.1.19338.19.2.3.53
		p2pENQ11 OBJECT-IDENTITY
			STATUS current
			DESCRIPTION 
				"Description."
			::= { network2 53 }

		
		-- 1.3.6.1.4.1.19338.19.2.3.53.1
		totalINCount156 OBJECT-TYPE
			SYNTAX OCTET STRING
			MAX-ACCESS read-write
			STATUS current
			DESCRIPTION
				"Description."
			::= { p2pENQ11 1 }

		
		-- 1.3.6.1.4.1.19338.19.2.3.53.2
		successCount156 OBJECT-TYPE
			SYNTAX OCTET STRING
			MAX-ACCESS read-write
			STATUS current
			DESCRIPTION
				"Description."
			::= { p2pENQ11 2 }

		
		-- 1.3.6.1.4.1.19338.19.2.3.53.3
		failCount156 OBJECT-TYPE
			SYNTAX OCTET STRING
			MAX-ACCESS read-write
			STATUS current
			DESCRIPTION
				"Description."
			::= { p2pENQ11 3 }

		
		-- 1.3.6.1.4.1.19338.19.2.3.53.4
		refusedCount156 OBJECT-TYPE
			SYNTAX OCTET STRING
			MAX-ACCESS read-write
			STATUS current
			DESCRIPTION
				"Description."
			::= { p2pENQ11 4 }

		
		-- 1.3.6.1.4.1.19338.19.2.3.54
		p2pENQ21 OBJECT-IDENTITY
			STATUS current
			DESCRIPTION 
				"Description."
			::= { network2 54 }

		
		-- 1.3.6.1.4.1.19338.19.2.3.54.1
		totalINCount157 OBJECT-TYPE
			SYNTAX OCTET STRING
			MAX-ACCESS read-write
			STATUS current
			DESCRIPTION
				"Description."
			::= { p2pENQ21 1 }

		
		-- 1.3.6.1.4.1.19338.19.2.3.54.2
		successCount157 OBJECT-TYPE
			SYNTAX OCTET STRING
			MAX-ACCESS read-write
			STATUS current
			DESCRIPTION
				"Description."
			::= { p2pENQ21 2 }

		
		-- 1.3.6.1.4.1.19338.19.2.3.54.3
		failCount157 OBJECT-TYPE
			SYNTAX OCTET STRING
			MAX-ACCESS read-write
			STATUS current
			DESCRIPTION
				"Description."
			::= { p2pENQ21 3 }

		
		-- 1.3.6.1.4.1.19338.19.2.3.54.4
		refusedCount157 OBJECT-TYPE
			SYNTAX OCTET STRING
			MAX-ACCESS read-write
			STATUS current
			DESCRIPTION
				"Description."
			::= { p2pENQ21 4 }

		
		-- 1.3.6.1.4.1.19338.19.2.3.55
		pACCST1 OBJECT-IDENTITY
			STATUS current
			DESCRIPTION 
				"Description."
			::= { network2 55 }

		
		-- 1.3.6.1.4.1.19338.19.2.3.55.1
		totalINCount158 OBJECT-TYPE
			SYNTAX OCTET STRING
			MAX-ACCESS read-write
			STATUS current
			DESCRIPTION
				"Description."
			::= { pACCST1 1 }

		
		-- 1.3.6.1.4.1.19338.19.2.3.55.2
		successCount158 OBJECT-TYPE
			SYNTAX OCTET STRING
			MAX-ACCESS read-write
			STATUS current
			DESCRIPTION
				"Description."
			::= { pACCST1 2 }

		
		-- 1.3.6.1.4.1.19338.19.2.3.55.3
		failCount158 OBJECT-TYPE
			SYNTAX OCTET STRING
			MAX-ACCESS read-write
			STATUS current
			DESCRIPTION
				"Description."
			::= { pACCST1 3 }

		
		-- 1.3.6.1.4.1.19338.19.2.3.55.4
		refusedCount158 OBJECT-TYPE
			SYNTAX OCTET STRING
			MAX-ACCESS read-write
			STATUS current
			DESCRIPTION
				"Description."
			::= { pACCST1 4 }

		
		-- 1.3.6.1.4.1.19338.19.2.3.56
		pADD1 OBJECT-IDENTITY
			STATUS current
			DESCRIPTION 
				"Description."
			::= { network2 56 }

		
		-- 1.3.6.1.4.1.19338.19.2.3.56.1
		totalINCount159 OBJECT-TYPE
			SYNTAX OCTET STRING
			MAX-ACCESS read-write
			STATUS current
			DESCRIPTION
				"Description."
			::= { pADD1 1 }

		
		-- 1.3.6.1.4.1.19338.19.2.3.56.2
		successCount159 OBJECT-TYPE
			SYNTAX OCTET STRING
			MAX-ACCESS read-write
			STATUS current
			DESCRIPTION
				"Description."
			::= { pADD1 2 }

		
		-- 1.3.6.1.4.1.19338.19.2.3.56.3
		failCount159 OBJECT-TYPE
			SYNTAX OCTET STRING
			MAX-ACCESS read-write
			STATUS current
			DESCRIPTION
				"Description."
			::= { pADD1 3 }

		
		-- 1.3.6.1.4.1.19338.19.2.3.56.4
		refusedCount159 OBJECT-TYPE
			SYNTAX OCTET STRING
			MAX-ACCESS read-write
			STATUS current
			DESCRIPTION
				"Description."
			::= { pADD1 4 }

		
		-- 1.3.6.1.4.1.19338.19.2.3.57
		pBAR1 OBJECT-IDENTITY
			STATUS current
			DESCRIPTION 
				"Description."
			::= { network2 57 }

		
		-- 1.3.6.1.4.1.19338.19.2.3.57.1
		totalINCount160 OBJECT-TYPE
			SYNTAX OCTET STRING
			MAX-ACCESS read-write
			STATUS current
			DESCRIPTION
				"Description."
			::= { pBAR1 1 }

		
		-- 1.3.6.1.4.1.19338.19.2.3.57.2
		successCount160 OBJECT-TYPE
			SYNTAX OCTET STRING
			MAX-ACCESS read-write
			STATUS current
			DESCRIPTION
				"Description."
			::= { pBAR1 2 }

		
		-- 1.3.6.1.4.1.19338.19.2.3.57.3
		failCount160 OBJECT-TYPE
			SYNTAX OCTET STRING
			MAX-ACCESS read-write
			STATUS current
			DESCRIPTION
				"Description."
			::= { pBAR1 3 }

		
		-- 1.3.6.1.4.1.19338.19.2.3.57.4
		refusedCount160 OBJECT-TYPE
			SYNTAX OCTET STRING
			MAX-ACCESS read-write
			STATUS current
			DESCRIPTION
				"Description."
			::= { pBAR1 4 }

		
		-- 1.3.6.1.4.1.19338.19.2.3.58
		pCHLAN1 OBJECT-IDENTITY
			STATUS current
			DESCRIPTION 
				"Description."
			::= { network2 58 }

		
		-- 1.3.6.1.4.1.19338.19.2.3.58.1
		totalINCount161 OBJECT-TYPE
			SYNTAX OCTET STRING
			MAX-ACCESS read-write
			STATUS current
			DESCRIPTION
				"Description."
			::= { pCHLAN1 1 }

		
		-- 1.3.6.1.4.1.19338.19.2.3.58.2
		successCount161 OBJECT-TYPE
			SYNTAX OCTET STRING
			MAX-ACCESS read-write
			STATUS current
			DESCRIPTION
				"Description."
			::= { pCHLAN1 2 }

		
		-- 1.3.6.1.4.1.19338.19.2.3.58.3
		failCount161 OBJECT-TYPE
			SYNTAX OCTET STRING
			MAX-ACCESS read-write
			STATUS current
			DESCRIPTION
				"Description."
			::= { pCHLAN1 3 }

		
		-- 1.3.6.1.4.1.19338.19.2.3.58.4
		refusedCount161 OBJECT-TYPE
			SYNTAX OCTET STRING
			MAX-ACCESS read-write
			STATUS current
			DESCRIPTION
				"Description."
			::= { pCHLAN1 4 }

		
		-- 1.3.6.1.4.1.19338.19.2.3.59
		pCNF1 OBJECT-IDENTITY
			STATUS current
			DESCRIPTION 
				"Description."
			::= { network2 59 }

		
		-- 1.3.6.1.4.1.19338.19.2.3.59.1
		totalINCount162 OBJECT-TYPE
			SYNTAX OCTET STRING
			MAX-ACCESS read-write
			STATUS current
			DESCRIPTION
				"Description."
			::= { pCNF1 1 }

		
		-- 1.3.6.1.4.1.19338.19.2.3.59.2
		successCount162 OBJECT-TYPE
			SYNTAX OCTET STRING
			MAX-ACCESS read-write
			STATUS current
			DESCRIPTION
				"Description."
			::= { pCNF1 2 }

		
		-- 1.3.6.1.4.1.19338.19.2.3.59.3
		failCount162 OBJECT-TYPE
			SYNTAX OCTET STRING
			MAX-ACCESS read-write
			STATUS current
			DESCRIPTION
				"Description."
			::= { pCNF1 3 }

		
		-- 1.3.6.1.4.1.19338.19.2.3.59.4
		refusedCount162 OBJECT-TYPE
			SYNTAX OCTET STRING
			MAX-ACCESS read-write
			STATUS current
			DESCRIPTION
				"Description."
			::= { pCNF1 4 }

		
		-- 1.3.6.1.4.1.19338.19.2.3.60
		pcr1 OBJECT-IDENTITY
			STATUS current
			DESCRIPTION 
				"Description."
			::= { network2 60 }

		
		-- 1.3.6.1.4.1.19338.19.2.3.60.1
		totalINCount163 OBJECT-TYPE
			SYNTAX OCTET STRING
			MAX-ACCESS read-write
			STATUS current
			DESCRIPTION
				"Description."
			::= { pcr1 1 }

		
		-- 1.3.6.1.4.1.19338.19.2.3.60.2
		successCount163 OBJECT-TYPE
			SYNTAX OCTET STRING
			MAX-ACCESS read-write
			STATUS current
			DESCRIPTION
				"Description."
			::= { pcr1 2 }

		
		-- 1.3.6.1.4.1.19338.19.2.3.60.3
		failCount163 OBJECT-TYPE
			SYNTAX OCTET STRING
			MAX-ACCESS read-write
			STATUS current
			DESCRIPTION
				"Description."
			::= { pcr1 3 }

		
		-- 1.3.6.1.4.1.19338.19.2.3.60.4
		refusedCount163 OBJECT-TYPE
			SYNTAX OCTET STRING
			MAX-ACCESS read-write
			STATUS current
			DESCRIPTION
				"Description."
			::= { pcr1 4 }

		
		-- 1.3.6.1.4.1.19338.19.2.3.61
		pDEL1 OBJECT-IDENTITY
			STATUS current
			DESCRIPTION 
				"Description."
			::= { network2 61 }

		
		-- 1.3.6.1.4.1.19338.19.2.3.61.1
		totalINCount164 OBJECT-TYPE
			SYNTAX OCTET STRING
			MAX-ACCESS read-write
			STATUS current
			DESCRIPTION
				"Description."
			::= { pDEL1 1 }

		
		-- 1.3.6.1.4.1.19338.19.2.3.61.2
		successCount164 OBJECT-TYPE
			SYNTAX OCTET STRING
			MAX-ACCESS read-write
			STATUS current
			DESCRIPTION
				"Description."
			::= { pDEL1 2 }

		
		-- 1.3.6.1.4.1.19338.19.2.3.61.3
		failCount164 OBJECT-TYPE
			SYNTAX OCTET STRING
			MAX-ACCESS read-write
			STATUS current
			DESCRIPTION
				"Description."
			::= { pDEL1 3 }

		
		-- 1.3.6.1.4.1.19338.19.2.3.61.4
		refusedCount164 OBJECT-TYPE
			SYNTAX OCTET STRING
			MAX-ACCESS read-write
			STATUS current
			DESCRIPTION
				"Description."
			::= { pDEL1 4 }

		
		-- 1.3.6.1.4.1.19338.19.2.3.62
		pdREG1 OBJECT-IDENTITY
			STATUS current
			DESCRIPTION 
				"Description."
			::= { network2 62 }

		
		-- 1.3.6.1.4.1.19338.19.2.3.62.1
		totalINCount165 OBJECT-TYPE
			SYNTAX OCTET STRING
			MAX-ACCESS read-write
			STATUS current
			DESCRIPTION
				"Description."
			::= { pdREG1 1 }

		
		-- 1.3.6.1.4.1.19338.19.2.3.62.2
		successCount165 OBJECT-TYPE
			SYNTAX OCTET STRING
			MAX-ACCESS read-write
			STATUS current
			DESCRIPTION
				"Description."
			::= { pdREG1 2 }

		
		-- 1.3.6.1.4.1.19338.19.2.3.62.3
		failCount165 OBJECT-TYPE
			SYNTAX OCTET STRING
			MAX-ACCESS read-write
			STATUS current
			DESCRIPTION
				"Description."
			::= { pdREG1 3 }

		
		-- 1.3.6.1.4.1.19338.19.2.3.62.4
		refusedCount165 OBJECT-TYPE
			SYNTAX OCTET STRING
			MAX-ACCESS read-write
			STATUS current
			DESCRIPTION
				"Description."
			::= { pdREG1 4 }

		
		-- 1.3.6.1.4.1.19338.19.2.3.63
		pList1 OBJECT-IDENTITY
			STATUS current
			DESCRIPTION 
				"Description."
			::= { network2 63 }

		
		-- 1.3.6.1.4.1.19338.19.2.3.63.1
		totalINCount166 OBJECT-TYPE
			SYNTAX OCTET STRING
			MAX-ACCESS read-write
			STATUS current
			DESCRIPTION
				"Description."
			::= { pList1 1 }

		
		-- 1.3.6.1.4.1.19338.19.2.3.63.2
		successCount166 OBJECT-TYPE
			SYNTAX OCTET STRING
			MAX-ACCESS read-write
			STATUS current
			DESCRIPTION
				"Description."
			::= { pList1 2 }

		
		-- 1.3.6.1.4.1.19338.19.2.3.63.3
		failCount166 OBJECT-TYPE
			SYNTAX OCTET STRING
			MAX-ACCESS read-write
			STATUS current
			DESCRIPTION
				"Description."
			::= { pList1 3 }

		
		-- 1.3.6.1.4.1.19338.19.2.3.63.4
		refusedCount166 OBJECT-TYPE
			SYNTAX OCTET STRING
			MAX-ACCESS read-write
			STATUS current
			DESCRIPTION
				"Description."
			::= { pList1 4 }

		
		-- 1.3.6.1.4.1.19338.19.2.3.64
		plt1 OBJECT-IDENTITY
			STATUS current
			DESCRIPTION 
				"Description."
			::= { network2 64 }

		
		-- 1.3.6.1.4.1.19338.19.2.3.64.1
		totalINCount167 OBJECT-TYPE
			SYNTAX OCTET STRING
			MAX-ACCESS read-write
			STATUS current
			DESCRIPTION
				"Description."
			::= { plt1 1 }

		
		-- 1.3.6.1.4.1.19338.19.2.3.64.2
		successCount167 OBJECT-TYPE
			SYNTAX OCTET STRING
			MAX-ACCESS read-write
			STATUS current
			DESCRIPTION
				"Description."
			::= { plt1 2 }

		
		-- 1.3.6.1.4.1.19338.19.2.3.64.3
		failCount167 OBJECT-TYPE
			SYNTAX OCTET STRING
			MAX-ACCESS read-write
			STATUS current
			DESCRIPTION
				"Description."
			::= { plt1 3 }

		
		-- 1.3.6.1.4.1.19338.19.2.3.64.4
		refusedCount167 OBJECT-TYPE
			SYNTAX OCTET STRING
			MAX-ACCESS read-write
			STATUS current
			DESCRIPTION
				"Description."
			::= { plt1 4 }

		
		-- 1.3.6.1.4.1.19338.19.2.3.65
		ppb1 OBJECT-IDENTITY
			STATUS current
			DESCRIPTION 
				"Description."
			::= { network2 65 }

		
		-- 1.3.6.1.4.1.19338.19.2.3.65.1
		totalINCount168 OBJECT-TYPE
			SYNTAX OCTET STRING
			MAX-ACCESS read-write
			STATUS current
			DESCRIPTION
				"Description."
			::= { ppb1 1 }

		
		-- 1.3.6.1.4.1.19338.19.2.3.65.2
		successCount168 OBJECT-TYPE
			SYNTAX OCTET STRING
			MAX-ACCESS read-write
			STATUS current
			DESCRIPTION
				"Description."
			::= { ppb1 2 }

		
		-- 1.3.6.1.4.1.19338.19.2.3.65.3
		failCount168 OBJECT-TYPE
			SYNTAX OCTET STRING
			MAX-ACCESS read-write
			STATUS current
			DESCRIPTION
				"Description."
			::= { ppb1 3 }

		
		-- 1.3.6.1.4.1.19338.19.2.3.65.4
		refusedCount168 OBJECT-TYPE
			SYNTAX OCTET STRING
			MAX-ACCESS read-write
			STATUS current
			DESCRIPTION
				"Description."
			::= { ppb1 4 }

		
		-- 1.3.6.1.4.1.19338.19.2.3.66
		ppel1 OBJECT-IDENTITY
			STATUS current
			DESCRIPTION 
				"Description."
			::= { network2 66 }

		
		-- 1.3.6.1.4.1.19338.19.2.3.66.1
		totalINCount169 OBJECT-TYPE
			SYNTAX OCTET STRING
			MAX-ACCESS read-write
			STATUS current
			DESCRIPTION
				"Description."
			::= { ppel1 1 }

		
		-- 1.3.6.1.4.1.19338.19.2.3.66.2
		successCount169 OBJECT-TYPE
			SYNTAX OCTET STRING
			MAX-ACCESS read-write
			STATUS current
			DESCRIPTION
				"Description."
			::= { ppel1 2 }

		
		-- 1.3.6.1.4.1.19338.19.2.3.66.3
		failCount169 OBJECT-TYPE
			SYNTAX OCTET STRING
			MAX-ACCESS read-write
			STATUS current
			DESCRIPTION
				"Description."
			::= { ppel1 3 }

		
		-- 1.3.6.1.4.1.19338.19.2.3.66.4
		refusedCount169 OBJECT-TYPE
			SYNTAX OCTET STRING
			MAX-ACCESS read-write
			STATUS current
			DESCRIPTION
				"Description."
			::= { ppel1 4 }

		
		-- 1.3.6.1.4.1.19338.19.2.3.67
		pr1 OBJECT-IDENTITY
			STATUS current
			DESCRIPTION 
				"Description."
			::= { network2 67 }

		
		-- 1.3.6.1.4.1.19338.19.2.3.67.1
		totalINCount170 OBJECT-TYPE
			SYNTAX OCTET STRING
			MAX-ACCESS read-write
			STATUS current
			DESCRIPTION
				"Description."
			::= { pr1 1 }

		
		-- 1.3.6.1.4.1.19338.19.2.3.67.2
		successCount170 OBJECT-TYPE
			SYNTAX OCTET STRING
			MAX-ACCESS read-write
			STATUS current
			DESCRIPTION
				"Description."
			::= { pr1 2 }

		
		-- 1.3.6.1.4.1.19338.19.2.3.67.3
		failCount170 OBJECT-TYPE
			SYNTAX OCTET STRING
			MAX-ACCESS read-write
			STATUS current
			DESCRIPTION
				"Description."
			::= { pr1 3 }

		
		-- 1.3.6.1.4.1.19338.19.2.3.67.4
		refusedCount170 OBJECT-TYPE
			SYNTAX OCTET STRING
			MAX-ACCESS read-write
			STATUS current
			DESCRIPTION
				"Description."
			::= { pr1 4 }

		
		-- 1.3.6.1.4.1.19338.19.2.3.68
		prc1 OBJECT-IDENTITY
			STATUS current
			DESCRIPTION 
				"Description."
			::= { network2 68 }

		
		-- 1.3.6.1.4.1.19338.19.2.3.68.1
		totalINCount171 OBJECT-TYPE
			SYNTAX OCTET STRING
			MAX-ACCESS read-write
			STATUS current
			DESCRIPTION
				"Description."
			::= { prc1 1 }

		
		-- 1.3.6.1.4.1.19338.19.2.3.68.2
		successCount171 OBJECT-TYPE
			SYNTAX OCTET STRING
			MAX-ACCESS read-write
			STATUS current
			DESCRIPTION
				"Description."
			::= { prc1 2 }

		
		-- 1.3.6.1.4.1.19338.19.2.3.68.3
		failCount171 OBJECT-TYPE
			SYNTAX OCTET STRING
			MAX-ACCESS read-write
			STATUS current
			DESCRIPTION
				"Description."
			::= { prc1 3 }

		
		-- 1.3.6.1.4.1.19338.19.2.3.68.4
		refusedCount171 OBJECT-TYPE
			SYNTAX OCTET STRING
			MAX-ACCESS read-write
			STATUS current
			DESCRIPTION
				"Description."
			::= { prc1 4 }

		
		-- 1.3.6.1.4.1.19338.19.2.3.69
		pRCMDA1 OBJECT-IDENTITY
			STATUS current
			DESCRIPTION 
				"Description."
			::= { network2 69 }

		
		-- 1.3.6.1.4.1.19338.19.2.3.69.1
		totalINCount172 OBJECT-TYPE
			SYNTAX OCTET STRING
			MAX-ACCESS read-write
			STATUS current
			DESCRIPTION
				"Description."
			::= { pRCMDA1 1 }

		
		-- 1.3.6.1.4.1.19338.19.2.3.69.2
		successCount172 OBJECT-TYPE
			SYNTAX OCTET STRING
			MAX-ACCESS read-write
			STATUS current
			DESCRIPTION
				"Description."
			::= { pRCMDA1 2 }

		
		-- 1.3.6.1.4.1.19338.19.2.3.69.3
		failCount172 OBJECT-TYPE
			SYNTAX OCTET STRING
			MAX-ACCESS read-write
			STATUS current
			DESCRIPTION
				"Description."
			::= { pRCMDA1 3 }

		
		-- 1.3.6.1.4.1.19338.19.2.3.69.4
		refusedCount172 OBJECT-TYPE
			SYNTAX OCTET STRING
			MAX-ACCESS read-write
			STATUS current
			DESCRIPTION
				"Description."
			::= { pRCMDA1 4 }

		
		-- 1.3.6.1.4.1.19338.19.2.3.70
		preg1 OBJECT-IDENTITY
			STATUS current
			DESCRIPTION 
				"Description."
			::= { network2 70 }

		
		-- 1.3.6.1.4.1.19338.19.2.3.70.1
		totalINCount173 OBJECT-TYPE
			SYNTAX OCTET STRING
			MAX-ACCESS read-write
			STATUS current
			DESCRIPTION
				"Description."
			::= { preg1 1 }

		
		-- 1.3.6.1.4.1.19338.19.2.3.70.2
		successCount173 OBJECT-TYPE
			SYNTAX OCTET STRING
			MAX-ACCESS read-write
			STATUS current
			DESCRIPTION
				"Description."
			::= { preg1 2 }

		
		-- 1.3.6.1.4.1.19338.19.2.3.70.3
		failCount173 OBJECT-TYPE
			SYNTAX OCTET STRING
			MAX-ACCESS read-write
			STATUS current
			DESCRIPTION
				"Description."
			::= { preg1 3 }

		
		-- 1.3.6.1.4.1.19338.19.2.3.70.4
		refusedCount173 OBJECT-TYPE
			SYNTAX OCTET STRING
			MAX-ACCESS read-write
			STATUS current
			DESCRIPTION
				"Description."
			::= { preg1 4 }

		
		-- 1.3.6.1.4.1.19338.19.2.3.71
		pres1 OBJECT-IDENTITY
			STATUS current
			DESCRIPTION 
				"Description."
			::= { network2 71 }

		
		-- 1.3.6.1.4.1.19338.19.2.3.71.1
		totalINCount174 OBJECT-TYPE
			SYNTAX OCTET STRING
			MAX-ACCESS read-write
			STATUS current
			DESCRIPTION
				"Description."
			::= { pres1 1 }

		
		-- 1.3.6.1.4.1.19338.19.2.3.71.2
		successCount174 OBJECT-TYPE
			SYNTAX OCTET STRING
			MAX-ACCESS read-write
			STATUS current
			DESCRIPTION
				"Description."
			::= { pres1 2 }

		
		-- 1.3.6.1.4.1.19338.19.2.3.71.3
		failCount174 OBJECT-TYPE
			SYNTAX OCTET STRING
			MAX-ACCESS read-write
			STATUS current
			DESCRIPTION
				"Description."
			::= { pres1 3 }

		
		-- 1.3.6.1.4.1.19338.19.2.3.71.4
		refusedCount174 OBJECT-TYPE
			SYNTAX OCTET STRING
			MAX-ACCESS read-write
			STATUS current
			DESCRIPTION
				"Description."
			::= { pres1 4 }

		
		-- 1.3.6.1.4.1.19338.19.2.3.72
		ps1 OBJECT-IDENTITY
			STATUS current
			DESCRIPTION 
				"Description."
			::= { network2 72 }

		
		-- 1.3.6.1.4.1.19338.19.2.3.72.1
		totalINCount175 OBJECT-TYPE
			SYNTAX OCTET STRING
			MAX-ACCESS read-write
			STATUS current
			DESCRIPTION
				"Description."
			::= { ps1 1 }

		
		-- 1.3.6.1.4.1.19338.19.2.3.72.2
		successCount175 OBJECT-TYPE
			SYNTAX OCTET STRING
			MAX-ACCESS read-write
			STATUS current
			DESCRIPTION
				"Description."
			::= { ps1 2 }

		
		-- 1.3.6.1.4.1.19338.19.2.3.72.3
		failCount175 OBJECT-TYPE
			SYNTAX OCTET STRING
			MAX-ACCESS read-write
			STATUS current
			DESCRIPTION
				"Description."
			::= { ps1 3 }

		
		-- 1.3.6.1.4.1.19338.19.2.3.72.4
		refusedCount175 OBJECT-TYPE
			SYNTAX OCTET STRING
			MAX-ACCESS read-write
			STATUS current
			DESCRIPTION
				"Description."
			::= { ps1 4 }

		
		-- 1.3.6.1.4.1.19338.19.2.3.73
		pSTNRC1 OBJECT-IDENTITY
			STATUS current
			DESCRIPTION 
				"Description."
			::= { network2 73 }

		
		-- 1.3.6.1.4.1.19338.19.2.3.73.1
		totalINCount176 OBJECT-TYPE
			SYNTAX OCTET STRING
			MAX-ACCESS read-write
			STATUS current
			DESCRIPTION
				"Description."
			::= { pSTNRC1 1 }

		
		-- 1.3.6.1.4.1.19338.19.2.3.73.2
		successCount176 OBJECT-TYPE
			SYNTAX OCTET STRING
			MAX-ACCESS read-write
			STATUS current
			DESCRIPTION
				"Description."
			::= { pSTNRC1 2 }

		
		-- 1.3.6.1.4.1.19338.19.2.3.73.3
		failCount176 OBJECT-TYPE
			SYNTAX OCTET STRING
			MAX-ACCESS read-write
			STATUS current
			DESCRIPTION
				"Description."
			::= { pSTNRC1 3 }

		
		-- 1.3.6.1.4.1.19338.19.2.3.73.4
		refusedCount176 OBJECT-TYPE
			SYNTAX OCTET STRING
			MAX-ACCESS read-write
			STATUS current
			DESCRIPTION
				"Description."
			::= { pSTNRC1 4 }

		
		-- 1.3.6.1.4.1.19338.19.2.3.74
		pSUS1 OBJECT-IDENTITY
			STATUS current
			DESCRIPTION 
				"Description."
			::= { network2 74 }

		
		-- 1.3.6.1.4.1.19338.19.2.3.74.1
		totalINCount177 OBJECT-TYPE
			SYNTAX OCTET STRING
			MAX-ACCESS read-write
			STATUS current
			DESCRIPTION
				"Description."
			::= { pSUS1 1 }

		
		-- 1.3.6.1.4.1.19338.19.2.3.74.2
		successCount177 OBJECT-TYPE
			SYNTAX OCTET STRING
			MAX-ACCESS read-write
			STATUS current
			DESCRIPTION
				"Description."
			::= { pSUS1 2 }

		
		-- 1.3.6.1.4.1.19338.19.2.3.74.3
		failCount177 OBJECT-TYPE
			SYNTAX OCTET STRING
			MAX-ACCESS read-write
			STATUS current
			DESCRIPTION
				"Description."
			::= { pSUS1 3 }

		
		-- 1.3.6.1.4.1.19338.19.2.3.74.4
		refusedCount177 OBJECT-TYPE
			SYNTAX OCTET STRING
			MAX-ACCESS read-write
			STATUS current
			DESCRIPTION
				"Description."
			::= { pSUS1 4 }

		
		-- 1.3.6.1.4.1.19338.19.2.3.75
		ptr1 OBJECT-IDENTITY
			STATUS current
			DESCRIPTION 
				"Description."
			::= { network2 75 }

		
		-- 1.3.6.1.4.1.19338.19.2.3.75.1
		totalINCount178 OBJECT-TYPE
			SYNTAX OCTET STRING
			MAX-ACCESS read-write
			STATUS current
			DESCRIPTION
				"Description."
			::= { ptr1 1 }

		
		-- 1.3.6.1.4.1.19338.19.2.3.75.2
		successCount178 OBJECT-TYPE
			SYNTAX OCTET STRING
			MAX-ACCESS read-write
			STATUS current
			DESCRIPTION
				"Description."
			::= { ptr1 2 }

		
		-- 1.3.6.1.4.1.19338.19.2.3.75.3
		failCount178 OBJECT-TYPE
			SYNTAX OCTET STRING
			MAX-ACCESS read-write
			STATUS current
			DESCRIPTION
				"Description."
			::= { ptr1 3 }

		
		-- 1.3.6.1.4.1.19338.19.2.3.75.4
		refusedCount178 OBJECT-TYPE
			SYNTAX OCTET STRING
			MAX-ACCESS read-write
			STATUS current
			DESCRIPTION
				"Description."
			::= { ptr1 4 }

		
		-- 1.3.6.1.4.1.19338.19.2.3.76
		pVAS1 OBJECT-IDENTITY
			STATUS current
			DESCRIPTION 
				"Description."
			::= { network2 76 }

		
		-- 1.3.6.1.4.1.19338.19.2.3.76.1
		totalINCount179 OBJECT-TYPE
			SYNTAX OCTET STRING
			MAX-ACCESS read-write
			STATUS current
			DESCRIPTION
				"Description."
			::= { pVAS1 1 }

		
		-- 1.3.6.1.4.1.19338.19.2.3.76.2
		successCount179 OBJECT-TYPE
			SYNTAX OCTET STRING
			MAX-ACCESS read-write
			STATUS current
			DESCRIPTION
				"Description."
			::= { pVAS1 2 }

		
		-- 1.3.6.1.4.1.19338.19.2.3.76.3
		failCount179 OBJECT-TYPE
			SYNTAX OCTET STRING
			MAX-ACCESS read-write
			STATUS current
			DESCRIPTION
				"Description."
			::= { pVAS1 3 }

		
		-- 1.3.6.1.4.1.19338.19.2.3.76.4
		refusedCount179 OBJECT-TYPE
			SYNTAX OCTET STRING
			MAX-ACCESS read-write
			STATUS current
			DESCRIPTION
				"Description."
			::= { pVAS1 4 }

		
		-- 1.3.6.1.4.1.19338.19.2.3.77
		rc1 OBJECT-IDENTITY
			STATUS current
			DESCRIPTION 
				"Description."
			::= { network2 77 }

		
		-- 1.3.6.1.4.1.19338.19.2.3.77.1
		totalINCount180 OBJECT-TYPE
			SYNTAX OCTET STRING
			MAX-ACCESS read-write
			STATUS current
			DESCRIPTION
				"Description."
			::= { rc1 1 }

		
		-- 1.3.6.1.4.1.19338.19.2.3.77.2
		successCount180 OBJECT-TYPE
			SYNTAX OCTET STRING
			MAX-ACCESS read-write
			STATUS current
			DESCRIPTION
				"Description."
			::= { rc1 2 }

		
		-- 1.3.6.1.4.1.19338.19.2.3.77.3
		failCount180 OBJECT-TYPE
			SYNTAX OCTET STRING
			MAX-ACCESS read-write
			STATUS current
			DESCRIPTION
				"Description."
			::= { rc1 3 }

		
		-- 1.3.6.1.4.1.19338.19.2.3.77.4
		refusedCount180 OBJECT-TYPE
			SYNTAX OCTET STRING
			MAX-ACCESS read-write
			STATUS current
			DESCRIPTION
				"Description."
			::= { rc1 4 }

		
		-- 1.3.6.1.4.1.19338.19.2.3.78
		rce1 OBJECT-IDENTITY
			STATUS current
			DESCRIPTION 
				"Description."
			::= { network2 78 }

		
		-- 1.3.6.1.4.1.19338.19.2.3.78.1
		totalINCount181 OBJECT-TYPE
			SYNTAX OCTET STRING
			MAX-ACCESS read-write
			STATUS current
			DESCRIPTION
				"Description."
			::= { rce1 1 }

		
		-- 1.3.6.1.4.1.19338.19.2.3.78.2
		successCount181 OBJECT-TYPE
			SYNTAX OCTET STRING
			MAX-ACCESS read-write
			STATUS current
			DESCRIPTION
				"Description."
			::= { rce1 2 }

		
		-- 1.3.6.1.4.1.19338.19.2.3.78.3
		failCount181 OBJECT-TYPE
			SYNTAX OCTET STRING
			MAX-ACCESS read-write
			STATUS current
			DESCRIPTION
				"Description."
			::= { rce1 3 }

		
		-- 1.3.6.1.4.1.19338.19.2.3.78.4
		refusedCount181 OBJECT-TYPE
			SYNTAX OCTET STRING
			MAX-ACCESS read-write
			STATUS current
			DESCRIPTION
				"Description."
			::= { rce1 4 }

		
		-- 1.3.6.1.4.1.19338.19.2.3.79
		regSID1 OBJECT-IDENTITY
			STATUS current
			DESCRIPTION 
				"Description."
			::= { network2 79 }

		
		-- 1.3.6.1.4.1.19338.19.2.3.79.1
		totalINCount182 OBJECT-TYPE
			SYNTAX OCTET STRING
			MAX-ACCESS read-write
			STATUS current
			DESCRIPTION
				"Description."
			::= { regSID1 1 }

		
		-- 1.3.6.1.4.1.19338.19.2.3.79.2
		successCount182 OBJECT-TYPE
			SYNTAX OCTET STRING
			MAX-ACCESS read-write
			STATUS current
			DESCRIPTION
				"Description."
			::= { regSID1 2 }

		
		-- 1.3.6.1.4.1.19338.19.2.3.79.3
		failCount182 OBJECT-TYPE
			SYNTAX OCTET STRING
			MAX-ACCESS read-write
			STATUS current
			DESCRIPTION
				"Description."
			::= { regSID1 3 }

		
		-- 1.3.6.1.4.1.19338.19.2.3.79.4
		refusedCount182 OBJECT-TYPE
			SYNTAX OCTET STRING
			MAX-ACCESS read-write
			STATUS current
			DESCRIPTION
				"Description."
			::= { regSID1 4 }

		
		-- 1.3.6.1.4.1.19338.19.2.3.80
		resP2PSER1 OBJECT-IDENTITY
			STATUS current
			DESCRIPTION 
				"Description."
			::= { network2 80 }

		
		-- 1.3.6.1.4.1.19338.19.2.3.80.1
		totalINCount183 OBJECT-TYPE
			SYNTAX OCTET STRING
			MAX-ACCESS read-write
			STATUS current
			DESCRIPTION
				"Description."
			::= { resP2PSER1 1 }

		
		-- 1.3.6.1.4.1.19338.19.2.3.80.2
		successCount183 OBJECT-TYPE
			SYNTAX OCTET STRING
			MAX-ACCESS read-write
			STATUS current
			DESCRIPTION
				"Description."
			::= { resP2PSER1 2 }

		
		-- 1.3.6.1.4.1.19338.19.2.3.80.3
		failCount183 OBJECT-TYPE
			SYNTAX OCTET STRING
			MAX-ACCESS read-write
			STATUS current
			DESCRIPTION
				"Description."
			::= { resP2PSER1 3 }

		
		-- 1.3.6.1.4.1.19338.19.2.3.80.4
		refusedCount183 OBJECT-TYPE
			SYNTAX OCTET STRING
			MAX-ACCESS read-write
			STATUS current
			DESCRIPTION
				"Description."
			::= { resP2PSER1 4 }

		
		-- 1.3.6.1.4.1.19338.19.2.3.81
		ret1 OBJECT-IDENTITY
			STATUS current
			DESCRIPTION 
				"Description."
			::= { network2 81 }

		
		-- 1.3.6.1.4.1.19338.19.2.3.81.1
		totalINCount184 OBJECT-TYPE
			SYNTAX OCTET STRING
			MAX-ACCESS read-write
			STATUS current
			DESCRIPTION
				"Description."
			::= { ret1 1 }

		
		-- 1.3.6.1.4.1.19338.19.2.3.81.2
		successCount184 OBJECT-TYPE
			SYNTAX OCTET STRING
			MAX-ACCESS read-write
			STATUS current
			DESCRIPTION
				"Description."
			::= { ret1 2 }

		
		-- 1.3.6.1.4.1.19338.19.2.3.81.3
		failCount184 OBJECT-TYPE
			SYNTAX OCTET STRING
			MAX-ACCESS read-write
			STATUS current
			DESCRIPTION
				"Description."
			::= { ret1 3 }

		
		-- 1.3.6.1.4.1.19338.19.2.3.81.4
		refusedCount184 OBJECT-TYPE
			SYNTAX OCTET STRING
			MAX-ACCESS read-write
			STATUS current
			DESCRIPTION
				"Description."
			::= { ret1 4 }

		
		-- 1.3.6.1.4.1.19338.19.2.3.82
		rr1 OBJECT-IDENTITY
			STATUS current
			DESCRIPTION 
				"Description."
			::= { network2 82 }

		
		-- 1.3.6.1.4.1.19338.19.2.3.82.1
		totalINCount185 OBJECT-TYPE
			SYNTAX OCTET STRING
			MAX-ACCESS read-write
			STATUS current
			DESCRIPTION
				"Description."
			::= { rr1 1 }

		
		-- 1.3.6.1.4.1.19338.19.2.3.82.2
		successCount185 OBJECT-TYPE
			SYNTAX OCTET STRING
			MAX-ACCESS read-write
			STATUS current
			DESCRIPTION
				"Description."
			::= { rr1 2 }

		
		-- 1.3.6.1.4.1.19338.19.2.3.82.3
		failCount185 OBJECT-TYPE
			SYNTAX OCTET STRING
			MAX-ACCESS read-write
			STATUS current
			DESCRIPTION
				"Description."
			::= { rr1 3 }

		
		-- 1.3.6.1.4.1.19338.19.2.3.82.4
		refusedCount185 OBJECT-TYPE
			SYNTAX OCTET STRING
			MAX-ACCESS read-write
			STATUS current
			DESCRIPTION
				"Description."
			::= { rr1 4 }

		
		-- 1.3.6.1.4.1.19338.19.2.3.83
		rs1 OBJECT-IDENTITY
			STATUS current
			DESCRIPTION 
				"Description."
			::= { network2 83 }

		
		-- 1.3.6.1.4.1.19338.19.2.3.83.1
		totalINCount186 OBJECT-TYPE
			SYNTAX OCTET STRING
			MAX-ACCESS read-write
			STATUS current
			DESCRIPTION
				"Description."
			::= { rs1 1 }

		
		-- 1.3.6.1.4.1.19338.19.2.3.83.2
		successCount186 OBJECT-TYPE
			SYNTAX OCTET STRING
			MAX-ACCESS read-write
			STATUS current
			DESCRIPTION
				"Description."
			::= { rs1 2 }

		
		-- 1.3.6.1.4.1.19338.19.2.3.83.3
		failCount186 OBJECT-TYPE
			SYNTAX OCTET STRING
			MAX-ACCESS read-write
			STATUS current
			DESCRIPTION
				"Description."
			::= { rs1 3 }

		
		-- 1.3.6.1.4.1.19338.19.2.3.83.4
		refusedCount186 OBJECT-TYPE
			SYNTAX OCTET STRING
			MAX-ACCESS read-write
			STATUS current
			DESCRIPTION
				"Description."
			::= { rs1 4 }

		
		-- 1.3.6.1.4.1.19338.19.2.3.84
		rub1 OBJECT-IDENTITY
			STATUS current
			DESCRIPTION 
				"Description."
			::= { network2 84 }

		
		-- 1.3.6.1.4.1.19338.19.2.3.84.1
		totalINCount187 OBJECT-TYPE
			SYNTAX OCTET STRING
			MAX-ACCESS read-write
			STATUS current
			DESCRIPTION
				"Description."
			::= { rub1 1 }

		
		-- 1.3.6.1.4.1.19338.19.2.3.84.2
		successCount187 OBJECT-TYPE
			SYNTAX OCTET STRING
			MAX-ACCESS read-write
			STATUS current
			DESCRIPTION
				"Description."
			::= { rub1 2 }

		
		-- 1.3.6.1.4.1.19338.19.2.3.84.3
		failCount187 OBJECT-TYPE
			SYNTAX OCTET STRING
			MAX-ACCESS read-write
			STATUS current
			DESCRIPTION
				"Description."
			::= { rub1 3 }

		
		-- 1.3.6.1.4.1.19338.19.2.3.84.4
		refusedCount187 OBJECT-TYPE
			SYNTAX OCTET STRING
			MAX-ACCESS read-write
			STATUS current
			DESCRIPTION
				"Description."
			::= { rub1 4 }

		
		-- 1.3.6.1.4.1.19338.19.2.3.85
		simACT1 OBJECT-IDENTITY
			STATUS current
			DESCRIPTION 
				"Description."
			::= { network2 85 }

		
		-- 1.3.6.1.4.1.19338.19.2.3.85.1
		totalINCount188 OBJECT-TYPE
			SYNTAX OCTET STRING
			MAX-ACCESS read-write
			STATUS current
			DESCRIPTION
				"Description."
			::= { simACT1 1 }

		
		-- 1.3.6.1.4.1.19338.19.2.3.85.2
		successCount188 OBJECT-TYPE
			SYNTAX OCTET STRING
			MAX-ACCESS read-write
			STATUS current
			DESCRIPTION
				"Description."
			::= { simACT1 2 }

		
		-- 1.3.6.1.4.1.19338.19.2.3.85.3
		failCount188 OBJECT-TYPE
			SYNTAX OCTET STRING
			MAX-ACCESS read-write
			STATUS current
			DESCRIPTION
				"Description."
			::= { simACT1 3 }

		
		-- 1.3.6.1.4.1.19338.19.2.3.85.4
		refusedCount188 OBJECT-TYPE
			SYNTAX OCTET STRING
			MAX-ACCESS read-write
			STATUS current
			DESCRIPTION
				"Description."
			::= { simACT1 4 }

		
		-- 1.3.6.1.4.1.19338.19.2.3.86
		sos1 OBJECT-IDENTITY
			STATUS current
			DESCRIPTION 
				"Description."
			::= { network2 86 }

		
		-- 1.3.6.1.4.1.19338.19.2.3.86.1
		totalINCount189 OBJECT-TYPE
			SYNTAX OCTET STRING
			MAX-ACCESS read-write
			STATUS current
			DESCRIPTION
				"Description."
			::= { sos1 1 }

		
		-- 1.3.6.1.4.1.19338.19.2.3.86.2
		successCount189 OBJECT-TYPE
			SYNTAX OCTET STRING
			MAX-ACCESS read-write
			STATUS current
			DESCRIPTION
				"Description."
			::= { sos1 2 }

		
		-- 1.3.6.1.4.1.19338.19.2.3.86.3
		failCount189 OBJECT-TYPE
			SYNTAX OCTET STRING
			MAX-ACCESS read-write
			STATUS current
			DESCRIPTION
				"Description."
			::= { sos1 3 }

		
		-- 1.3.6.1.4.1.19338.19.2.3.86.4
		refusedCount189 OBJECT-TYPE
			SYNTAX OCTET STRING
			MAX-ACCESS read-write
			STATUS current
			DESCRIPTION
				"Description."
			::= { sos1 4 }

		
		-- 1.3.6.1.4.1.19338.19.2.3.87
		sprc1 OBJECT-IDENTITY
			STATUS current
			DESCRIPTION 
				"Description."
			::= { network2 87 }

		
		-- 1.3.6.1.4.1.19338.19.2.3.87.1
		totalINCount190 OBJECT-TYPE
			SYNTAX OCTET STRING
			MAX-ACCESS read-write
			STATUS current
			DESCRIPTION
				"Description."
			::= { sprc1 1 }

		
		-- 1.3.6.1.4.1.19338.19.2.3.87.2
		successCount190 OBJECT-TYPE
			SYNTAX OCTET STRING
			MAX-ACCESS read-write
			STATUS current
			DESCRIPTION
				"Description."
			::= { sprc1 2 }

		
		-- 1.3.6.1.4.1.19338.19.2.3.87.3
		failCount190 OBJECT-TYPE
			SYNTAX OCTET STRING
			MAX-ACCESS read-write
			STATUS current
			DESCRIPTION
				"Description."
			::= { sprc1 3 }

		
		-- 1.3.6.1.4.1.19338.19.2.3.87.4
		refusedCount190 OBJECT-TYPE
			SYNTAX OCTET STRING
			MAX-ACCESS read-write
			STATUS current
			DESCRIPTION
				"Description."
			::= { sprc1 4 }

		
		-- 1.3.6.1.4.1.19338.19.2.3.88
		sub1 OBJECT-IDENTITY
			STATUS current
			DESCRIPTION 
				"Description."
			::= { network2 88 }

		
		-- 1.3.6.1.4.1.19338.19.2.3.88.1
		totalINCount191 OBJECT-TYPE
			SYNTAX OCTET STRING
			MAX-ACCESS read-write
			STATUS current
			DESCRIPTION
				"Description."
			::= { sub1 1 }

		
		-- 1.3.6.1.4.1.19338.19.2.3.88.2
		successCount191 OBJECT-TYPE
			SYNTAX OCTET STRING
			MAX-ACCESS read-write
			STATUS current
			DESCRIPTION
				"Description."
			::= { sub1 2 }

		
		-- 1.3.6.1.4.1.19338.19.2.3.88.3
		failCount191 OBJECT-TYPE
			SYNTAX OCTET STRING
			MAX-ACCESS read-write
			STATUS current
			DESCRIPTION
				"Description."
			::= { sub1 3 }

		
		-- 1.3.6.1.4.1.19338.19.2.3.88.4
		refusedCount191 OBJECT-TYPE
			SYNTAX OCTET STRING
			MAX-ACCESS read-write
			STATUS current
			DESCRIPTION
				"Description."
			::= { sub1 4 }

		
		-- 1.3.6.1.4.1.19338.19.2.3.89
		susP2PSER1 OBJECT-IDENTITY
			STATUS current
			DESCRIPTION 
				"Description."
			::= { network2 89 }

		
		-- 1.3.6.1.4.1.19338.19.2.3.89.1
		totalINCount192 OBJECT-TYPE
			SYNTAX OCTET STRING
			MAX-ACCESS read-write
			STATUS current
			DESCRIPTION
				"Description."
			::= { susP2PSER1 1 }

		
		-- 1.3.6.1.4.1.19338.19.2.3.89.2
		successCount192 OBJECT-TYPE
			SYNTAX OCTET STRING
			MAX-ACCESS read-write
			STATUS current
			DESCRIPTION
				"Description."
			::= { susP2PSER1 2 }

		
		-- 1.3.6.1.4.1.19338.19.2.3.89.3
		failCount192 OBJECT-TYPE
			SYNTAX OCTET STRING
			MAX-ACCESS read-write
			STATUS current
			DESCRIPTION
				"Description."
			::= { susP2PSER1 3 }

		
		-- 1.3.6.1.4.1.19338.19.2.3.89.4
		refusedCount192 OBJECT-TYPE
			SYNTAX OCTET STRING
			MAX-ACCESS read-write
			STATUS current
			DESCRIPTION
				"Description."
			::= { susP2PSER1 4 }

		
		-- 1.3.6.1.4.1.19338.19.2.3.90
		susRESUSR1 OBJECT-IDENTITY
			STATUS current
			DESCRIPTION 
				"Description."
			::= { network2 90 }

		
		-- 1.3.6.1.4.1.19338.19.2.3.90.1
		totalINCount193 OBJECT-TYPE
			SYNTAX OCTET STRING
			MAX-ACCESS read-write
			STATUS current
			DESCRIPTION
				"Description."
			::= { susRESUSR1 1 }

		
		-- 1.3.6.1.4.1.19338.19.2.3.90.2
		successCount193 OBJECT-TYPE
			SYNTAX OCTET STRING
			MAX-ACCESS read-write
			STATUS current
			DESCRIPTION
				"Description."
			::= { susRESUSR1 2 }

		
		-- 1.3.6.1.4.1.19338.19.2.3.90.3
		failCount193 OBJECT-TYPE
			SYNTAX OCTET STRING
			MAX-ACCESS read-write
			STATUS current
			DESCRIPTION
				"Description."
			::= { susRESUSR1 3 }

		
		-- 1.3.6.1.4.1.19338.19.2.3.90.4
		refusedCount193 OBJECT-TYPE
			SYNTAX OCTET STRING
			MAX-ACCESS read-write
			STATUS current
			DESCRIPTION
				"Description."
			::= { susRESUSR1 4 }

		
		-- 1.3.6.1.4.1.19338.19.2.3.91
		trf1 OBJECT-IDENTITY
			STATUS current
			DESCRIPTION 
				"Description."
			::= { network2 91 }

		
		-- 1.3.6.1.4.1.19338.19.2.3.91.1
		totalINCount194 OBJECT-TYPE
			SYNTAX OCTET STRING
			MAX-ACCESS read-write
			STATUS current
			DESCRIPTION
				"Description."
			::= { trf1 1 }

		
		-- 1.3.6.1.4.1.19338.19.2.3.91.2
		successCount194 OBJECT-TYPE
			SYNTAX OCTET STRING
			MAX-ACCESS read-write
			STATUS current
			DESCRIPTION
				"Description."
			::= { trf1 2 }

		
		-- 1.3.6.1.4.1.19338.19.2.3.91.3
		failCount194 OBJECT-TYPE
			SYNTAX OCTET STRING
			MAX-ACCESS read-write
			STATUS current
			DESCRIPTION
				"Description."
			::= { trf1 3 }

		
		-- 1.3.6.1.4.1.19338.19.2.3.91.4
		refusedCount194 OBJECT-TYPE
			SYNTAX OCTET STRING
			MAX-ACCESS read-write
			STATUS current
			DESCRIPTION
				"Description."
			::= { trf1 4 }

		
		-- 1.3.6.1.4.1.19338.19.2.3.92
		trfRULETYP1 OBJECT-IDENTITY
			STATUS current
			DESCRIPTION 
				"Description."
			::= { network2 92 }

		
		-- 1.3.6.1.4.1.19338.19.2.3.92.1
		totalINCount195 OBJECT-TYPE
			SYNTAX OCTET STRING
			MAX-ACCESS read-write
			STATUS current
			DESCRIPTION
				"Description."
			::= { trfRULETYP1 1 }

		
		-- 1.3.6.1.4.1.19338.19.2.3.92.2
		successCount195 OBJECT-TYPE
			SYNTAX OCTET STRING
			MAX-ACCESS read-write
			STATUS current
			DESCRIPTION
				"Description."
			::= { trfRULETYP1 2 }

		
		-- 1.3.6.1.4.1.19338.19.2.3.92.3
		failCount195 OBJECT-TYPE
			SYNTAX OCTET STRING
			MAX-ACCESS read-write
			STATUS current
			DESCRIPTION
				"Description."
			::= { trfRULETYP1 3 }

		
		-- 1.3.6.1.4.1.19338.19.2.3.92.4
		refusedCount195 OBJECT-TYPE
			SYNTAX OCTET STRING
			MAX-ACCESS read-write
			STATUS current
			DESCRIPTION
				"Description."
			::= { trfRULETYP1 4 }

		
		-- 1.3.6.1.4.1.19338.19.2.3.93
		ubp1 OBJECT-IDENTITY
			STATUS current
			DESCRIPTION 
				"Description."
			::= { network2 93 }

		
		-- 1.3.6.1.4.1.19338.19.2.3.93.1
		totalINCount196 OBJECT-TYPE
			SYNTAX OCTET STRING
			MAX-ACCESS read-write
			STATUS current
			DESCRIPTION
				"Description."
			::= { ubp1 1 }

		
		-- 1.3.6.1.4.1.19338.19.2.3.93.2
		successCount196 OBJECT-TYPE
			SYNTAX OCTET STRING
			MAX-ACCESS read-write
			STATUS current
			DESCRIPTION
				"Description."
			::= { ubp1 2 }

		
		-- 1.3.6.1.4.1.19338.19.2.3.93.3
		failCount196 OBJECT-TYPE
			SYNTAX OCTET STRING
			MAX-ACCESS read-write
			STATUS current
			DESCRIPTION
				"Description."
			::= { ubp1 3 }

		
		-- 1.3.6.1.4.1.19338.19.2.3.93.4
		refusedCount196 OBJECT-TYPE
			SYNTAX OCTET STRING
			MAX-ACCESS read-write
			STATUS current
			DESCRIPTION
				"Description."
			::= { ubp1 4 }

		
		-- 1.3.6.1.4.1.19338.19.2.3.94
		unBARUSER1 OBJECT-IDENTITY
			STATUS current
			DESCRIPTION 
				"Description."
			::= { network2 94 }

		
		-- 1.3.6.1.4.1.19338.19.2.3.94.1
		totalINCount197 OBJECT-TYPE
			SYNTAX OCTET STRING
			MAX-ACCESS read-write
			STATUS current
			DESCRIPTION
				"Description."
			::= { unBARUSER1 1 }

		
		-- 1.3.6.1.4.1.19338.19.2.3.94.2
		successCount197 OBJECT-TYPE
			SYNTAX OCTET STRING
			MAX-ACCESS read-write
			STATUS current
			DESCRIPTION
				"Description."
			::= { unBARUSER1 2 }

		
		-- 1.3.6.1.4.1.19338.19.2.3.94.3
		failCount197 OBJECT-TYPE
			SYNTAX OCTET STRING
			MAX-ACCESS read-write
			STATUS current
			DESCRIPTION
				"Description."
			::= { unBARUSER1 3 }

		
		-- 1.3.6.1.4.1.19338.19.2.3.94.4
		refusedCount197 OBJECT-TYPE
			SYNTAX OCTET STRING
			MAX-ACCESS read-write
			STATUS current
			DESCRIPTION
				"Description."
			::= { unBARUSER1 4 }

		
		-- 1.3.6.1.4.1.19338.19.2.3.95
		usrAUTH1 OBJECT-IDENTITY
			STATUS current
			DESCRIPTION 
				"Description."
			::= { network2 95 }

		
		-- 1.3.6.1.4.1.19338.19.2.3.95.1
		totalINCount198 OBJECT-TYPE
			SYNTAX OCTET STRING
			MAX-ACCESS read-write
			STATUS current
			DESCRIPTION
				"Description."
			::= { usrAUTH1 1 }

		
		-- 1.3.6.1.4.1.19338.19.2.3.95.2
		successCount198 OBJECT-TYPE
			SYNTAX OCTET STRING
			MAX-ACCESS read-write
			STATUS current
			DESCRIPTION
				"Description."
			::= { usrAUTH1 2 }

		
		-- 1.3.6.1.4.1.19338.19.2.3.95.3
		failCount198 OBJECT-TYPE
			SYNTAX OCTET STRING
			MAX-ACCESS read-write
			STATUS current
			DESCRIPTION
				"Description."
			::= { usrAUTH1 3 }

		
		-- 1.3.6.1.4.1.19338.19.2.3.95.4
		refusedCount198 OBJECT-TYPE
			SYNTAX OCTET STRING
			MAX-ACCESS read-write
			STATUS current
			DESCRIPTION
				"Description."
			::= { usrAUTH1 4 }

		
		-- 1.3.6.1.4.1.19338.19.2.3.96
		usrRG1 OBJECT-IDENTITY
			STATUS current
			DESCRIPTION 
				"Description."
			::= { network2 96 }

		
		-- 1.3.6.1.4.1.19338.19.2.3.96.1
		totalINCount199 OBJECT-TYPE
			SYNTAX OCTET STRING
			MAX-ACCESS read-write
			STATUS current
			DESCRIPTION
				"Description."
			::= { usrRG1 1 }

		
		-- 1.3.6.1.4.1.19338.19.2.3.96.2
		successCount199 OBJECT-TYPE
			SYNTAX OCTET STRING
			MAX-ACCESS read-write
			STATUS current
			DESCRIPTION
				"Description."
			::= { usrRG1 2 }

		
		-- 1.3.6.1.4.1.19338.19.2.3.96.3
		failCount199 OBJECT-TYPE
			SYNTAX OCTET STRING
			MAX-ACCESS read-write
			STATUS current
			DESCRIPTION
				"Description."
			::= { usrRG1 3 }

		
		-- 1.3.6.1.4.1.19338.19.2.3.96.4
		refusedCount199 OBJECT-TYPE
			SYNTAX OCTET STRING
			MAX-ACCESS read-write
			STATUS current
			DESCRIPTION
				"Description."
			::= { usrRG1 4 }

		
		-- 1.3.6.1.4.1.19338.19.2.3.97
		vas1 OBJECT-IDENTITY
			STATUS current
			DESCRIPTION 
				"Description."
			::= { network2 97 }

		
		-- 1.3.6.1.4.1.19338.19.2.3.97.1
		totalINCount200 OBJECT-TYPE
			SYNTAX OCTET STRING
			MAX-ACCESS read-write
			STATUS current
			DESCRIPTION
				"Description."
			::= { vas1 1 }

		
		-- 1.3.6.1.4.1.19338.19.2.3.97.2
		successCount200 OBJECT-TYPE
			SYNTAX OCTET STRING
			MAX-ACCESS read-write
			STATUS current
			DESCRIPTION
				"Description."
			::= { vas1 2 }

		
		-- 1.3.6.1.4.1.19338.19.2.3.97.3
		failCount200 OBJECT-TYPE
			SYNTAX OCTET STRING
			MAX-ACCESS read-write
			STATUS current
			DESCRIPTION
				"Description."
			::= { vas1 3 }

		
		-- 1.3.6.1.4.1.19338.19.2.3.97.4
		refusedCount200 OBJECT-TYPE
			SYNTAX OCTET STRING
			MAX-ACCESS read-write
			STATUS current
			DESCRIPTION
				"Description."
			::= { vas1 4 }

		
		-- 1.3.6.1.4.1.19338.19.2.3.98
		viewBARRED1 OBJECT-IDENTITY
			STATUS current
			DESCRIPTION 
				"Description."
			::= { network2 98 }

		
		-- 1.3.6.1.4.1.19338.19.2.3.98.1
		totalINCount201 OBJECT-TYPE
			SYNTAX OCTET STRING
			MAX-ACCESS read-write
			STATUS current
			DESCRIPTION
				"Description."
			::= { viewBARRED1 1 }

		
		-- 1.3.6.1.4.1.19338.19.2.3.98.2
		successCount201 OBJECT-TYPE
			SYNTAX OCTET STRING
			MAX-ACCESS read-write
			STATUS current
			DESCRIPTION
				"Description."
			::= { viewBARRED1 2 }

		
		-- 1.3.6.1.4.1.19338.19.2.3.98.3
		failCount201 OBJECT-TYPE
			SYNTAX OCTET STRING
			MAX-ACCESS read-write
			STATUS current
			DESCRIPTION
				"Description."
			::= { viewBARRED1 3 }

		
		-- 1.3.6.1.4.1.19338.19.2.3.98.4
		refusedCount201 OBJECT-TYPE
			SYNTAX OCTET STRING
			MAX-ACCESS read-write
			STATUS current
			DESCRIPTION
				"Description."
			::= { viewBARRED1 4 }

		
		-- 1.3.6.1.4.1.19338.19.2.3.99
		viewCUSER1 OBJECT-IDENTITY
			STATUS current
			DESCRIPTION 
				"Description."
			::= { network2 99 }

		
		-- 1.3.6.1.4.1.19338.19.2.3.99.1
		totalINCount202 OBJECT-TYPE
			SYNTAX OCTET STRING
			MAX-ACCESS read-write
			STATUS current
			DESCRIPTION
				"Description."
			::= { viewCUSER1 1 }

		
		-- 1.3.6.1.4.1.19338.19.2.3.99.2
		successCount202 OBJECT-TYPE
			SYNTAX OCTET STRING
			MAX-ACCESS read-write
			STATUS current
			DESCRIPTION
				"Description."
			::= { viewCUSER1 2 }

		
		-- 1.3.6.1.4.1.19338.19.2.3.99.3
		failCount202 OBJECT-TYPE
			SYNTAX OCTET STRING
			MAX-ACCESS read-write
			STATUS current
			DESCRIPTION
				"Description."
			::= { viewCUSER1 3 }

		
		-- 1.3.6.1.4.1.19338.19.2.3.99.4
		refusedCount202 OBJECT-TYPE
			SYNTAX OCTET STRING
			MAX-ACCESS read-write
			STATUS current
			DESCRIPTION
				"Description."
			::= { viewCUSER1 4 }

		
		-- 1.3.6.1.4.1.19338.19.2.3.100
		viewREGSUB1 OBJECT-IDENTITY
			STATUS current
			DESCRIPTION 
				"Description."
			::= { network2 100 }

		
		-- 1.3.6.1.4.1.19338.19.2.3.100.1
		totalINCount203 OBJECT-TYPE
			SYNTAX OCTET STRING
			MAX-ACCESS read-write
			STATUS current
			DESCRIPTION
				"Description."
			::= { viewREGSUB1 1 }

		
		-- 1.3.6.1.4.1.19338.19.2.3.100.2
		successCount203 OBJECT-TYPE
			SYNTAX OCTET STRING
			MAX-ACCESS read-write
			STATUS current
			DESCRIPTION
				"Description."
			::= { viewREGSUB1 2 }

		
		-- 1.3.6.1.4.1.19338.19.2.3.100.3
		failCount203 OBJECT-TYPE
			SYNTAX OCTET STRING
			MAX-ACCESS read-write
			STATUS current
			DESCRIPTION
				"Description."
			::= { viewREGSUB1 3 }

		
		-- 1.3.6.1.4.1.19338.19.2.3.100.4
		refusedCount203 OBJECT-TYPE
			SYNTAX OCTET STRING
			MAX-ACCESS read-write
			STATUS current
			DESCRIPTION
				"Description."
			::= { viewREGSUB1 4 }

		
		-- 1.3.6.1.4.1.19338.19.2.3.101
		viewTRF1 OBJECT-IDENTITY
			STATUS current
			DESCRIPTION 
				"Description."
			::= { network2 101 }

		
		-- 1.3.6.1.4.1.19338.19.2.3.101.1
		totalINCount204 OBJECT-TYPE
			SYNTAX OCTET STRING
			MAX-ACCESS read-write
			STATUS current
			DESCRIPTION
				"Description."
			::= { viewTRF1 1 }

		
		-- 1.3.6.1.4.1.19338.19.2.3.101.2
		successCount204 OBJECT-TYPE
			SYNTAX OCTET STRING
			MAX-ACCESS read-write
			STATUS current
			DESCRIPTION
				"Description."
			::= { viewTRF1 2 }

		
		-- 1.3.6.1.4.1.19338.19.2.3.101.3
		failCount204 OBJECT-TYPE
			SYNTAX OCTET STRING
			MAX-ACCESS read-write
			STATUS current
			DESCRIPTION
				"Description."
			::= { viewTRF1 3 }

		
		-- 1.3.6.1.4.1.19338.19.2.3.101.4
		refusedCount204 OBJECT-TYPE
			SYNTAX OCTET STRING
			MAX-ACCESS read-write
			STATUS current
			DESCRIPTION
				"Description."
			::= { viewTRF1 4 }

		
		-- 1.3.6.1.4.1.19338.19.2.3.102
		wd1 OBJECT-IDENTITY
			STATUS current
			DESCRIPTION 
				"Description."
			::= { network2 102 }

		
		-- 1.3.6.1.4.1.19338.19.2.3.102.1
		totalINCount205 OBJECT-TYPE
			SYNTAX OCTET STRING
			MAX-ACCESS read-write
			STATUS current
			DESCRIPTION
				"Description."
			::= { wd1 1 }

		
		-- 1.3.6.1.4.1.19338.19.2.3.102.2
		successCount205 OBJECT-TYPE
			SYNTAX OCTET STRING
			MAX-ACCESS read-write
			STATUS current
			DESCRIPTION
				"Description."
			::= { wd1 2 }

		
		-- 1.3.6.1.4.1.19338.19.2.3.102.3
		failCount205 OBJECT-TYPE
			SYNTAX OCTET STRING
			MAX-ACCESS read-write
			STATUS current
			DESCRIPTION
				"Description."
			::= { wd1 3 }

		
		-- 1.3.6.1.4.1.19338.19.2.3.102.4
		refusedCount205 OBJECT-TYPE
			SYNTAX OCTET STRING
			MAX-ACCESS read-write
			STATUS current
			DESCRIPTION
				"Description."
			::= { wd1 4 }

		
		-- 1.3.6.1.4.1.19338.19.2.3.103
		whtlstENQ1 OBJECT-IDENTITY
			STATUS current
			DESCRIPTION 
				"Description."
			::= { network2 103 }

		
		-- 1.3.6.1.4.1.19338.19.2.3.103.1
		totalINCount206 OBJECT-TYPE
			SYNTAX OCTET STRING
			MAX-ACCESS read-write
			STATUS current
			DESCRIPTION
				"Description."
			::= { whtlstENQ1 1 }

		
		-- 1.3.6.1.4.1.19338.19.2.3.103.2
		successCount206 OBJECT-TYPE
			SYNTAX OCTET STRING
			MAX-ACCESS read-write
			STATUS current
			DESCRIPTION
				"Description."
			::= { whtlstENQ1 2 }

		
		-- 1.3.6.1.4.1.19338.19.2.3.103.3
		failCount206 OBJECT-TYPE
			SYNTAX OCTET STRING
			MAX-ACCESS read-write
			STATUS current
			DESCRIPTION
				"Description."
			::= { whtlstENQ1 3 }

		
		-- 1.3.6.1.4.1.19338.19.2.3.103.4
		refusedCount206 OBJECT-TYPE
			SYNTAX OCTET STRING
			MAX-ACCESS read-write
			STATUS current
			DESCRIPTION
				"Description."
			::= { whtlstENQ1 4 }

		
	
	END

--
-- MahindraComviva-GNOC-PreTUPs-MIB.my
--
